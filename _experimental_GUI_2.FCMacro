from PySide import QtGui, QtCore
import FreeCAD,FreeCADGui,Part, os
import re
import Mesh
import random

from PySide.QtCore import QSettings
import json

# CHANGE THE LINE BELOW
path_to_ui = ".\\ui\\dialog.ui"

class OpenEMS:
	def getOpenEMSObjects(self, filterStr = ""):
		currentObjects = App.ActiveDocument.Objects
		
		objToExport = []
		
		for obj in currentObjects:
			if (len(filterStr) > 0 and re.search(filterStr, obj.Label)):
				objToExport.append(obj)
			elif (len(filterStr) == 0):
				objToExport.append(obj)
	
		return objToExport

	def getAllObjects(self):
		currentObjects = App.ActiveDocument.Objects	
		objList = []
		for obj in currentObjects:
			item = QtGui.QTreeWidgetItem([obj.Label])
			item.setIcon(0, QtGui.QIcon(".\\img\\object.png")) 
			objList.append(item)
		return objList

	#return all items, at least all top level
	def getAllTreeWidgetItems(self, treeWidget):
		root = treeWidget.invisibleRootItem()
		child_count = root.childCount()
		itemList = []
		for i in range(child_count):
			print('Copying tree widget item ' + root.child(i).data(0, QtCore.Qt.UserRole).getName())
			item = root.child(i)
			itemList.append(item.data(0, QtCore.Qt.UserRole))
		return itemList

# parent class for following settings items, it contains all function common for all classes
#
class SettingsItem:

	# initializer
	def serializeToString(self, name = "", type = ""):
		self.name = name
		self.type = type
		return "{}"

	# basic type property common for all kind of settings
	def getType(self):
		return self.type

	# basic type property common for all kind of settings
	def getName(self):
		return self.name

	def getUnitsAsNumber(self, units):
		if (units in ('pOhm','pH','pF', 'pm', 'pHz')):
			outNumber = 1e-9
		elif (units in ('uOhm','uH','uF', 'um', 'uHz')):
			outNumber = 1e-6
		elif (units in ('mOhm','mH','mF', 'mm', 'mHz')):
			outNumber = 1e-3
		elif (units in ('cm')):
			outNumber = 1e-2
		elif (units in ('Ohm','H','F', 'm', 'Hz')):
			outNumber = 1
		elif (units in ('kOhm','kH','kF', 'km', 'kHz')):
			outNumber = 1e3
		elif (units in ('MOhm','MH','MF', 'MHz')):
			outNumber = 1e6
		elif (units in ('GOhm','GH','GF', 'GHz')):
			outNumber = 1e9
		else:
			outNumber = 0
		return outNumber

# FreeCAD part object
#
class FreeCADSettingsItem(SettingsItem):
	def __init__(self, name = "", type = "FreeCADSettingItem"):
		self.name = name
		self.type = type
		return

	def serializeToString(self):
		serializedString = "{'name': '" + self.name #+ "', 'type': '
		serializedString += "}"
		return serializedString

# Grid settings
#	Fixed Count    - fixed number per axes
#	Fixed Distance - gridlines have fixed distance between them
#	User Defined   - user has to provide coordinates where lines should be
#
class GridSettingsItem(SettingsItem):
	def __init__(self, name = "", type = "", fixedCount = {'x':0, 'y':0, 'z':0}, fixedDistance = {'x':0, 'y':0, 'z':0}, userDefined = {'data':""}, units = "", xenabled = True, yenabled = True, zenabled = True):
		self.name = name
		self.type = type
		self.units = units
		self.xenabled = xenabled
		self.yenabled = yenabled
		self.zenabled = zenabled
		self.fixedCount = fixedCount
		self.fixedDistance = fixedDistance
		self.userDefined = userDefined

	#Return xyz distances, count or user defined array based what user asked for.
	def getXYZ(self):
		if (self.type == "Fixed Count"):
			return self.fixedCount
		if (self.type == "Fixed Distance"):
			return self.fixedDistance
		if (self.type == "User Defined"):
			return self.userDefined
	
	def getUnitAsScriptLine(self):
		return str(self.getUnitsAsNumber(self.units))

# Material settings, basic are epsilon and mue, kappa and sigma are extended
#	epsilon - permitivity
#	mue     - permeability
#	kappa   - susceptibility, coupling coefficient
#	sigma   - VSWR, coductivity, surface charfe
#
class MaterialSettingsItem(SettingsItem):
	def __init__(self, name = "", type = "", constants = {'epsilon':1.0, 'mue':1.0, 'kappa':0.0, 'sigma': 0.0}):
		self.name = name
		self.type = type
		self.constants = constants

	def serializeToString(self):
		serializedString = "{'name': '" + self.name
		serializedString += ", 'epsilon': " + str(self.constants['epsilon'])
		serializedString += ", 'mue': " + str(self.constants['mue'])
		serializedString += ", 'kappa': " + str(self.constants['kappa'])
		serializedString += ", 'sigma': " + str(self.constants['sigma'])
		serializedString += "}"
		return serializedString

	#def getAllItems(self):
	#	return super(MaterialSettingItem, self).getAllItems()

# Excitation settings, for input power where energy is floating into model
#	Sinusodial - input port is excitated by sinusodial electric field
#	Gaussian   - gaussian impulse at input port
#	Custom     - user has to define function of electric field at input port
#
class ExcitationSettingsItem(SettingsItem):
	def __init__(self, name = "", type = "", sinusodial = {'fc': 0}, gaussian = {'f0': 0, 'fc': 0}, custom = {'functionStr': '0'}, units = "Hz"):
		SettingsItem.__init__(self)
		self.name = name
		self.type = type
		self.sinusodial = sinusodial
		self.gaussian = gaussian
		self.custom = custom
		self.units = units
		return

	def serializeToString(self):
		serializedString = "{'name': '" + self.name + "', "
		serializedString += "'type': '" + self.type + "', "
		if (self.type == "sinusodial"):
			serializedString += "'fc': '" + str(self.sinusodial['fc']) + "', "
		if (self.type == "gaussian"):
			serializedString += "'f0': '" + str(self.gaussian['f0']) + "', 'fc': '" + str(self.gaussian['fc']) + "' "
		if (self.type == "custom"):
			serializedString += "'f': '" + str(self.custom['functionStr']) + "' "

		serializedString += "'units': \"" + self.units + "\""
		serializedString += "}"
		return serializedString

	def getType(self):
		return self.type

# Port settings
#	There are just few types of ports defined in OpenEMS:
#		- lumped
#		- microstrip
#		- circular waveguide
#		- rectangular waveguide
class PortSettingsItem(SettingsItem):
	def __init__(self, name = "", type = "", R = 0, RUnits = "", isActive = False):
		self.name = name
		self.type = type
		self.R = R
		self.RUnits = RUnits
		self.isActive = isActive
		return

	def serializeToString(self):
		serializedString = "{'name': '" + self.name
		serializedString += ", 'R': " + self.R
		serializedString += ", 'RUnits': '" + self.RUnits + "'"
		serializedString += ", 'isActive': " + str(self.isActive)
		if (self.type == "lumped"):
			serializedString += ", 'type': 'lumped'"
		if (self.type == "microstrip"):
			serializedString += ", 'type': 'microstrip'"
		if (self.type == "circular waveguide"):
			serializedString += ", 'type': 'circular waveguide'"
		if (self.type == "rectangular waveguide"):
			serializedString += ", 'type': 'rectangular waveguide'"
		serializedString += "}"
		return serializedString

	def getRUnits(self):
		return self.getUnitsAsNumber(self.RUnits)

# Smulation settings
#	f0
#	fc
#
class SimulationSettingsItem(SettingsItem):
	def __init__(self, name = "DefaultSimlationName", params='{"max_timestamps": 1e6, "min_decrement": 0}'):
		self.name = name
		self.params = {}
		self.params = json.loads(params)
		return

	def serializeToString(self):
		jsonStr = ""
		jsonStr +=  '{"name": "' + self.name + '", "params": '
		jsonStr +=  json.dumps(self.params)
		jsonStr +=  '}'
		return jsonStr

class LumpedPartSettingsItem(SettingsItem):
	def __init__(self, name = "DefaultSimlationName", params='{"R": 0, "RUnits": "Ohm", "REnabled": 0, "L": 0, "LUnits": "uH", "LEnabled": 0, "C": 0, "CUnits": "pF", "CEnabled": 0}'):
		self.name = name
		self.params = {}
		self.params = json.loads(params)
		return

	def serializeToString(self):
		jsonStr = ""
		jsonStr +=  '{"name": "' + self.name + '", "params": '
		jsonStr +=  json.dumps(self.params)
		jsonStr +=  '}'
		return jsonStr

	def getType(self):
		typeStr = ''
		if (self.params['LEnabled']):
			typeStr += 'L'
		if (self.params['REnabled']):
			typeStr += 'R'
		if (self.params['CEnabled']):
			typeStr += 'C'
		return typeStr

	def getUnits(self, type = ''):
		units = ''
		type = type.lower()
		if ('r' in type):
			units = self.params['RUnits'] 
		elif ('l' in type):
			units = self.params['LUnits'] 
		elif ('c' in type):
			units = self.params['CUnits'] 
		return self.getUnitsAsNumber(units)

	def getUnitsAsNumber(self, units):
		if (units in ('pOhm','pH','pF')):
			outNumber = 1e-9
		elif (units in ('uOhm','uH','uF')):
			outNumber = 1e-6
		elif (units in ('mOhm','mH','mF')):
			outNumber = 1e-3
		elif (units in ('Ohm','H','F')):
			outNumber = 1
		elif (units in ('kOhm','kH','kF')):
			outNumber = 1e3
		elif (units in ('MOhm','MH','MF')):
			outNumber = 1e6
		elif (units in ('GOhm','GH','GF')):
			outNumber = 1e9
		else:
			outNumber = 0
		return outNumber

	def getR(self):
		outStr = str(self.params['R']) + "*" + str(self.getUnits('R'))
		return outStr
	def getL(self):
		outStr = str(self.params['L']) + "*" + str(self.getUnits('L'))
		return outStr
	def getC(self):
		outStr = str(self.params['C']) + "*" + str(self.getUnits('C'))
		return outStr

#
# Main GUI panel class
#
class BoxTaskPanel:
	def __init__(self):

		#
		# LOCAL OPENEMS OBJECT
		#
		self.openEMSObj = OpenEMS()

		#
		# Change current path to script file folder
		#
		abspath = os.path.abspath(__file__)
		dname = os.path.dirname(abspath)
		os.chdir(dname)

		# this will create a Qt widget from our ui file
		self.form = FreeCADGui.PySideUic.loadUi(path_to_ui)

		#
		# TOP LEVEL ITEMS (excitation, grid, materials, ...)
		#
		self.initRightColumnTopLevelItems()

		#select first item
		topItem = self.form.objectAssignmentRightTreeWidget.itemAt(0,0)
		self.form.objectAssignmentRightTreeWidget.setCurrentItem(topItem)

		self.form.moveLeftButton.clicked.connect(self.onMoveLeft)
		self.form.moveRightButton.clicked.connect(self.onMoveRight)

		#########################################################################################################
		#	Left Column FreeCAD objects added in list
		#########################################################################################################

		self.initLeftColumnTopLevelItems()		

		#########################################################################################################
		#########################################################################################################
		#########################################################################################################

		#
		# SETTINGS FOR BUTTONS CLICK, functions assignments
		#
		self.form.gridSettingsAddButton.clicked.connect(self.gridSettingsAddButtonClicked)
		self.form.gridSettingsRemoveButton.clicked.connect(self.gridSettingsRemoveButtonClicked)
		self.form.gridSettingsRewriteButton.clicked.connect(self.gridSettingsRewriteButtonClicked)

		self.form.materialSettingsAddButton.clicked.connect(self.materialSettingsAddButtonClicked)
		self.form.materialSettingsRemoveButton.clicked.connect(self.materialSettingsRemoveButtonClicked)

		self.form.excitationSettingsAddButton.clicked.connect(self.excitationSettingsAddButtonClicked)
		self.form.excitationSettingsRemoveButton.clicked.connect(self.excitationSettingsRemoveButtonClicked)

		self.form.portSettingsAddButton.clicked.connect(self.portSettingsAddButtonClicked)
		self.form.portSettingsRemoveButton.clicked.connect(self.portSettingsRemoveButtonClicked)

		self.form.lumpedPartSettingsAddButton.clicked.connect(self.lumpedPartSettingsAddButtonClicked)
		self.form.lumpedPartSettingsRemoveButton.clicked.connect(self.lumpedPartSettingsRemoveButtonClicked)

		#
		# Handle function for grid radio buttons click
		#
		self.form.userDefinedRadioButton.clicked.connect(self.userDefinedRadioButtonClicked)
		self.form.fixedCountRadioButton.clicked.connect(self.fixedCountRadioButtonClicked)
		self.form.fixedDistanceRadioButton.clicked.connect(self.fixedDistanceRadioButtonClicked)

		# Handle function for MATERIAL RADIO BUTTONS
		self.form.materialUserDefinedRadioButton.toggled.connect(self.materialUserDeinedRadioButtonToggled)	

		#
		# Clicked on "Generate OpenEMS Script"
		#		
		self.form.generateOpenEMSScriptButton.clicked.connect(self.generateOpenEMSScriptButtonClicked)

		#
		# Material, Grid, Excitation, ... item changed handler functions.
		#		
		self.form.materialSettingsTreeView.currentItemChanged.connect(self.materialTreeWidgetItemChanged)	
		self.form.excitationSettingsTreeView.currentItemChanged.connect(self.excitationTreeWidgetItemChanged)	
		self.form.gridSettingsTreeView.currentItemChanged.connect(self.gridTreeWidgetItemChanged)	
		self.form.portSettingsTreeView.currentItemChanged.connect(self.portTreeWidgetItemChanged)	
		self.form.lumpedPartTreeView.currentItemChanged.connect(self.lumpedPartTreeWidgetItemChanged)	

		####################################################################################################
		# GUI SAVE/LOAD from file
		####################################################################################################
		self.form.saveCurrentSettingsButton.clicked.connect(self.saveCurrentSettingsButtonClicked)
		self.form.loadCurrentSettingsButton.clicked.connect(self.loadCurrentSettingsButtonClicked)

		#
		# FILTER LEFT COLUMN ITEMS
		#
		self.form.objectAssignmentFilterLeftButton.clicked.connect(self.objectAssignmentFilterLeftButtonClicked)

	def initLeftColumnTopLevelItems(self, filterStr = ""):
		self.form.objectAssignmentLeftTreeWidget.clear()
		openEMSObj = OpenEMS()

		items = openEMSObj.getOpenEMSObjects(filterStr)
		treeItems = []
		for i in items:
			print("openEMS object to export:" + i.Label)

			# FIRST METHOD raw including just labeled items
			#
			#item = QtGui.QTreeWidgetItem([i.Label])
			#item.setIcon(0, QtGui.QIcon(".\\img\\object.png"))
			#treeItems.append(item)

			# ADDING ITEMS with UserData object which storethem in intelligent way
			#
			topItem = QtGui.QTreeWidgetItem([i.Label])
			itemData = FreeCADSettingsItem(i.Label)
			topItem.setData(0, QtCore.Qt.UserRole, itemData)
			topItem.setIcon(0, QtGui.QIcon(".\\img\\object.png"))
			treeItems.append(topItem)
		
		self.form.objectAssignmentLeftTreeWidget.insertTopLevelItems(0, treeItems)

	def materialUserDeinedRadioButtonToggled(self):
		if (self.form.materialUserDefinedRadioButton.isChecked()):
			self.form.materialEpsilonNumberInput.setEnabled(True)
			self.form.materialMueNumberInput.setEnabled(True)
			self.form.materialKappaNumberInput.setEnabled(True)
			self.form.materialSigmaNumberInput.setEnabled(True)
		else:
			self.form.materialEpsilonNumberInput.setEnabled(False)
			self.form.materialMueNumberInput.setEnabled(False)
			self.form.materialKappaNumberInput.setEnabled(False)
			self.form.materialSigmaNumberInput.setEnabled(False)

	def objectAssignmentFilterLeftButtonClicked(self):
		print("Filter left column")
		filterStr = self.form.objectAssignmentFilterLeft.toPlainText()
		self.initLeftColumnTopLevelItems(filterStr)

	def initRightColumnTopLevelItems(self):
		#
		# Default items for each section
		#
		""" NO DEFAULT ITEMS!
		topItem = self.form.objectAssignmentRightTreeWidget.itemAt(0,0)
		defaultMaterialItem = QtGui.QTreeWidgetItem(["Material Default"])
		defaultExcitationItem = QtGui.QTreeWidgetItem(["Excitation Default"])
		defaultGridItem = QtGui.QTreeWidgetItem(["Grid Default"])
		defaultPortItem = QtGui.QTreeWidgetItem(["Port Default"])
		defaultLumpedPartItem = QtGui.QTreeWidgetItem(["LumpedPart Default"])
		"""

		#
		# Default items in each subsection have user data FreeCADSttingsItem classes to have just basic information like genereal freecad object
		#
		""" NO DEFAULT ITEMS!
		defaultMaterialItem.setData(0, QtCore.Qt.UserRole, FreeCADSettingsItem("Material Default"))
		defaultExcitationItem.setData(0, QtCore.Qt.UserRole, FreeCADSettingsItem("Excitation Default"))
		defaultGridItem.setData(0, QtCore.Qt.UserRole, FreeCADSettingsItem("Grid Default"))
		defaultPortItem.setData(0, QtCore.Qt.UserRole, FreeCADSettingsItem("Port Default"))
		defaultLumpedPartItem.setData(0, QtCore.Qt.UserRole, FreeCADSettingsItem("LumpedPart Default"))
		"""

		# MATERIALS
		topItem = QtGui.QTreeWidgetItem(["Material"])
		topItem.setIcon(0, QtGui.QIcon(".\\img\\material.png"))
		#topItem.addChildren([defaultMaterialItem])	#NO DEFAULT ITEM
		self.form.objectAssignmentRightTreeWidget.insertTopLevelItem(0, topItem)

		#LuboJ
		self.MaterialsItem = topItem	#aux item materials item to have some reference here to be sure for future access it

		# EXCITATION
		topItem = QtGui.QTreeWidgetItem(["Excitation"])
		topItem.setIcon(0, QtGui.QIcon(".\\img\\bulb.png"))
		#topItem.addChildren([defaultExcitationItem])	#NO DEFAULT ITEM
		self.form.objectAssignmentRightTreeWidget.insertTopLevelItem(0, topItem)

		# GRID
		topItem = QtGui.QTreeWidgetItem(["Grid"])
		topItem.setIcon(0, QtGui.QIcon(".\\img\\grid.png"))
		#topItem.addChildren([defaultGridItem])	#NO DEFAULT ITEM
		self.form.objectAssignmentRightTreeWidget.insertTopLevelItem(0, topItem)

		# PORTS
		topItem = QtGui.QTreeWidgetItem(["Port"])
		topItem.setIcon(0, QtGui.QIcon(".\\img\\port.png"))
		#topItem.addChildren([defaultPortItem])	#NO DEFAULT ITEM
		self.form.objectAssignmentRightTreeWidget.insertTopLevelItem(0, topItem)

		# LUMPED PART
		topItem = QtGui.QTreeWidgetItem(["LumpedPart"])
		topItem.setIcon(0, QtGui.QIcon(".\\img\\lumpedpart.png"))
		#topItem.addChildren([defaultLumpedPartItem])	#NO DEFAULT ITEM
		self.form.objectAssignmentRightTreeWidget.insertTopLevelItem(0, topItem)

		return

	def saveCurrentSettingsButtonClicked(self):
		print("objectAssignmentShowSettingsButtonClicked entered")

		#get reference to each category item
		allItems = []
		childCount = self.form.objectAssignmentRightTreeWidget.invisibleRootItem().childCount()
		for k in range(childCount):
			allItems.append(self.form.objectAssignmentRightTreeWidget.topLevelItem(k))

		#go through categories children
		#output their data inside
		for m in range(len(allItems)):
			currItem = allItems[m]
			for k in range(currItem.childCount()):
				item = currItem.child(k)
				itemData = item.data(0, QtCore.Qt.UserRole)
				print("User datatype: " + item.text(0) + " - " + str(type(itemData)))
				if (itemData):
					print(itemData.serializeToString())

		return

	def getCurrDir(self):
		programname = os.path.basename(App.ActiveDocument.FileName)
		programbase, ext = os.path.splitext(programname)  # extract basename and ext from filename
		programDir = os.path.dirname(App.ActiveDocument.FileName)
		programNameBase = programDir + '/' + programbase

		print('--->' + programNameBase)
		print('--->' + programDir)
		return [programDir, programNameBase]

	def getSimParamsUnitsStr(self):
		units = self.form.simParamsUnitsNumberInput.currentText()
		if (units == 'Hz'):
			units2 = ''
			pass
		elif(units == "kHz"):
			units2 = 'e3'
			pass
		elif(units == "MHz"):
			units2 = 'e6'
			pass
		elif(units == "GHz"):
			units2 = 'e9'
			pass
		return units2

	def getSimParamsFcStr(self):
		units = self.getSimParamsUnitsStr()
		return str(self.form.simParamFcNumberInput.value()) + units

	def getSimParamsF0Str(self):
		units = self.getSimParamsUnitsStr()
		return str(self.form.simParamF0NumberInput.value()) + units

	#
	# Universal function to add items into categories in GUI.
	#
	def addSettingsItemGui(self, settingsItem):
		treeItemName = settingsItem.name
		treeItem = QtGui.QTreeWidgetItem([treeItemName])

		itemTypeReg = re.search("__main__.(.*)SettingsItem", str(type(settingsItem)))
		typeStr = itemTypeReg.group(1)
		print(typeStr)

		treeItem.setIcon(0, QtGui.QIcon(".\\img\\" + typeStr.lower() + ".png"))
		treeItem.setData(0, QtCore.Qt.UserRole, settingsItem)

		#add item into excitation list
		treeWidgetRef = {}
		itemChangedRef = {}
		if (typeStr.lower() == "excitation"):
			treeWidgetRef = self.form.excitationSettingsTreeView
		elif (typeStr.lower() == "port"):
			treeWidgetRef = self.form.portSettingsTreeView
		elif (typeStr.lower() == "grid"):
			treeWidgetRef = self.form.gridSettingsTreeView
		elif (typeStr.lower() == "material"):
			treeWidgetRef = self.form.materialSettingsTreeView
		elif (typeStr.lower() == "lumpedpart"):
			treeWidgetRef = self.form.lumpedPartTreeView
		else:
			print('cannot assign item ' + typeStr)
			return

		treeWidgetRef.insertTopLevelItem(0, treeItem)
		treeWidgetRef.setCurrentItem(treeWidgetRef.topLevelItem(0))

		#adding excitation also into OBJCET ASSIGNMENT WINDOW
		targetGroup = self.form.objectAssignmentRightTreeWidget.findItems(typeStr, QtCore.Qt.MatchExactly)
		targetGroup[0].addChild(treeItem.clone())

	#########################################################################################################################
	#                                  _                       _       _          _ _      _            _ 
	#                                 | |                     (_)     | |        | (_)    | |          | |
	#   __ _  ___ _ __   ___ _ __ __ _| |_ ___   ___  ___ _ __ _ _ __ | |_    ___| |_  ___| | _____  __| |
	#  / _` |/ _ \ '_ \ / _ \ '__/ _` | __/ _ \ / __|/ __| '__| | '_ \| __|  / __| | |/ __| |/ / _ \/ _` |
	# | (_| |  __/ | | |  __/ | | (_| | ||  __/ \__ \ (__| |  | | |_) | |_  | (__| | | (__|   <  __/ (_| |
	#  \__, |\___|_| |_|\___|_|  \__,_|\__\___| |___/\___|_|  |_| .__/ \__|  \___|_|_|\___|_|\_\___|\__,_|
	#   __/ |                                                   | |                                       
	#  |___/                    
	#
	#	GENERATE SCRIPT CLICKED
	#
	def generateOpenEMSScriptButtonClicked(self):
		print("generateOpenEMSScriptButtonClicked() Hello.")

		#get reference to each category item
		#
		# HERE IS ORDER IN WHICH LIST WILL BE EXECUTED AND ITEMS WILL BE TRANSLATED STEP BY STEP based on their type
		#
		#   _____ ______ _______     _____ ______ _   _ ______ _____         _______ ______ _____     _____       _______ ______ _____  ____  _____  _____ ______  _____ 
		#  / ____|  ____|__   __|   / ____|  ____| \ | |  ____|  __ \     /\|__   __|  ____|  __ \   / ____|   /\|__   __|  ____/ ____|/ __ \|  __ \|_   _|  ____|/ ____|
		# | (___ | |__     | |     | |  __| |__  |  \| | |__  | |__) |   /  \  | |  | |__  | |  | | | |       /  \  | |  | |__ | |  __| |  | | |__) | | | | |__  | (___  
		#  \___ \|  __|    | |     | | |_ |  __| | . ` |  __| |  _  /   / /\ \ | |  |  __| | |  | | | |      / /\ \ | |  |  __|| | |_ | |  | |  _  /  | | |  __|  \___ \ 
		#  ____) | |____   | |     | |__| | |____| |\  | |____| | \ \  / ____ \| |  | |____| |__| | | |____ / ____ \| |  | |___| |__| | |__| | | \ \ _| |_| |____ ____) |
		# |_____/|______|  |_|      \_____|______|_| \_|______|_|  \_\/_/    \_\_|  |______|_____/   \_____/_/    \_\_|  |______\_____|\____/|_|  \_\_____|______|_____/ 
		#                                                                                                                                                               
		allItems = []
		childCount = self.form.objectAssignmentRightTreeWidget.invisibleRootItem().childCount()
		for k in range(childCount):
			allItems.append(self.form.objectAssignmentRightTreeWidget.topLevelItem(k))

		#go through categories children, output their data inside
		"""
		for m in range(len(allItems)):
			currItem = allItems[m]
			for k in range(currItem.childCount()):
				item = currItem.child(k)
				itemData = item.data(0, QtCore.Qt.UserRole)
				print("User datatype: " + item.text(0) + " - " + str(type(itemData)))
				if (itemData):
					print(itemData.serializeToString())
		"""

		# GENERATE OCTAVE SCRIPT FOR OPENEMS item by item
		genScript = ''

		#
		# Generating script beginning
		#
		genScript += "% EXAMPLE / generated file for openEMS from FreeCAD\n"
		genScript += "%\n"
		genScript += "% This is generated file\n"
		genScript += "%\n"
		genScript += "% FreeCAD to OpenEMS plugin by Lubomir Jagos\n"
		genScript += "%\n"
		genScript += "\n"
		genScript += "close all\n"
		genScript += "clear\n"
		genScript += "clc\n"
		genScript += "\n"
		genScript += "%% switches & options...\n"
		genScript += "postprocessing_only = 0;\n"
		genScript += "draw_3d_pattern = 0; % this may take a while...\n"
		genScript += "use_pml = 0;         % use pml boundaries instead of mur\n"
		genScript += "\n"
		genScript += "currDir = strrep(pwd(), '\\', '\\\\');\n"
		genScript += "\n"
		genScript += "%LuboJ, JUST TO SEE RESULT\n"
		genScript += "%openEMS_opts = '--no-simulation';\n"
		genScript += "%openEMS_opts = '--debug-PEC --no-simulation';\n"
		genScript += "openEMS_opts = '';\n"
		genScript += "\n"

		#
		# IMPORTANT
		#
		genScript += "%% setup the simulation\n"
		genScript += "physical_constants;\n"
		#genScript += "unit = " +  + "; % all length in mm\n"
		#genScript += "max_res = c0 / (f0+fc) / unit / 20; % cell size: lambda/20\n"

		#
		# SIMULATION SETTING, OK
		#
		genScript += "\n"
		genScript += "%% prepare simulation folder\n"
		genScript += "Sim_Path = 'tmp';\n"
		genScript += "Sim_CSX = '" + os.path.splitext(os.path.basename(App.ActiveDocument.FileName))[0] + ".xml';\n"
		genScript += "[status, message, messageid] = rmdir( Sim_Path, 's' ); % clear previous directory\n"
		genScript += "[status, message, messageid] = mkdir( Sim_Path ); % create empty simulation folder\n"
		genScript += "\n"
		genScript += "%% setup FDTD parameter & excitation function\n"
		genScript += "max_timesteps = " + str(self.form.simParamsMaxTimesteps.value())  + ";\n"
		genScript += "min_decrement = " + str(self.form.simParamsMinDecrement.value()) + "; % equivalent to -50 dB\n"
		genScript += "FDTD = InitFDTD( 'NrTS', max_timesteps, 'EndCriteria', min_decrement );\n"
		genScript += "\n"

		#default structure for mesh
		genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"
		genScript += "% MESH\n"
		genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"
		genScript += "mesh.x = [];\n"
		genScript += "mesh.y = [];\n"
		genScript += "mesh.z = [];\n"

		#
		#	EXCITATION
		#  ________   _______ _____ _______    _______ _____ ____  _   _                                   _           _                 _      
		# |  ____\ \ / / ____|_   _|__   __|/\|__   __|_   _/ __ \| \ | |                                 | |         | |               | |     
		# | |__   \ V / |      | |    | |  /  \  | |    | || |  | |  \| |   __ _  ___ _ __   ___ _ __ __ _| |_ ___  __| |   ___ ___   __| | ___ 
		# |  __|   > <| |      | |    | | / /\ \ | |    | || |  | | . ` |  / _` |/ _ \ '_ \ / _ \ '__/ _` | __/ _ \/ _` |  / __/ _ \ / _` |/ _ \
		# | |____ / . \ |____ _| |_   | |/ ____ \| |   _| || |__| | |\  | | (_| |  __/ | | |  __/ | | (_| | ||  __/ (_| | | (_| (_) | (_| |  __/
		# |______/_/ \_\_____|_____|  |_/_/    \_\_|  |_____\____/|_| \_|  \__, |\___|_| |_|\___|_|  \__,_|\__\___|\__,_|  \___\___/ \__,_|\___|
		#                                                                   __/ |                                                               
		#                                                                  |___/                                                                
		excitationCategory = self.form.objectAssignmentRightTreeWidget.findItems("Excitation", QtCore.Qt.MatchFixedString)
		if len(excitationCategory) >= 0:
			print("Excitation Settings detected")
			print("#")
			print("#EXCITATION")

			#FOR WHOLE SIMULATION THERE IS JUST ONE EXCITATION DEFINED, so first is taken!
			item = excitationCategory[0].child(1)
			currSetting = item.data(0, QtCore.Qt.UserRole)	#at index 0 is Default Excitation
			if (currSetting.getName() != 'Excitation Default'):
				print("#name: " + currSetting.getName())
				print("#type: " + currSetting.getType())

				#DON'T KNOW WHY I HAD THS IN EXCITATION BEFORE, I WILL SEE
				#portName = "port_" + str(100*m+k)

				#
				# EXCITATION openEMS GENERATION INTO VARIABLE
				#
				genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"
				genScript += "% EXCITATION " + currSetting.getName() + "\n"
				genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"

				if (currSetting.getType() == 'sinusodial'):
					genScript += "fc = " + str(currSetting.sinusodial['fc']) + ";\n"
					genScript += "FDTD = SetSinusExcite(FDTD,fc);\n"
					pass
				elif (currSetting.getType() == 'gaussian'):
					genScript += "f0 = " + str(currSetting.gaussian['f0']) + "*" + str(currSetting.getUnitsAsNumber(currSetting.units)) + ";\n"
					genScript += "fc = " + str(currSetting.gaussian['fc']) + ";\n"
					genScript += "FDTD = SetGaussExcite(FDTD, f0, fc );\n"
					pass
				elif (currSetting.getType() == 'custom'):
					genScript += "%custom\n"
					pass
				pass
			else:
				print("#Excitation Default")
				print("---")
				pass
			pass

		#
		# BOUNDARY CONDITIONS SETTING, OK
		#
		genScript += "BC = {'MUR' 'MUR' 'MUR' 'MUR' 'MUR' 'MUR'}; % boundary conditions\n"
		genScript += "if (use_pml>0)\n"
		genScript += "    BC = {'PML_8' 'PML_8' 'PML_8' 'PML_8' 'PML_8' 'PML_8'}; % use pml instead of mur\n"
		genScript += "end\n"
		genScript += "FDTD = SetBoundaryCond( FDTD, BC );\n"
		genScript += "\n"
		genScript += "CSX = InitCSX();\n"
		genScript += "\n"

		# GENERATE OCTAVE SCRIPT FOR OPENEMS item by item
		genScriptPortCount = 1

		print("======================== REPORT BEGIN ========================\n")
		for m in range(len(allItems)):
			currItem = allItems[m]

			for k in range(currItem.childCount()):
				item = currItem.child(k)
				itemData = item.data(0, QtCore.Qt.UserRole)
				if (itemData):
					#
					#	PORT
					#  ____    ____  _____ _______                                   _           _                 _      
					# |  __ \ / __ \|  __ \__   __|                                 | |         | |               | |     
					# | |__) | |  | | |__) | | |      __ _  ___ _ __   ___ _ __ __ _| |_ ___  __| |   ___ ___   __| | ___ 
					# |  ___/| |  | |  _  /  | |     / _` |/ _ \ '_ \ / _ \ '__/ _` | __/ _ \/ _` |  / __/ _ \ / _` |/ _ \
					# | |    | |__| | | \ \  | |    | (_| |  __/ | | |  __/ | | (_| | ||  __/ (_| | | (_| (_) | (_| |  __/
					# |_|     \____/|_|  \_\ |_|     \__, |\___|_| |_|\___|_|  \__,_|\__\___|\__,_|  \___\___/ \__,_|\___|
					#                                 __/ |                                                               
					#                                |___/                                                                
					#
					if (itemData.__class__.__name__ is "PortSettingsItem"):
						print("Port Settings detected")
						currSetting = item.data(0, QtCore.Qt.UserRole)
						print("#")
						print("#PORT")
						print("#name: " + currSetting.getName())
						print("#type: " + currSetting.getType())

						objs = FreeCAD.ActiveDocument.Objects
						for k in range(item.childCount()):
							childName = item.child(k).text(0)

							genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"
							genScript += "% PORT - " + currSetting.getName() + " - " + childName + "\n"
							genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"

							print("##Children:")
							print("\t" + childName)
							freecadObjects = [i for i in objs if (i.Label) == childName] 

							#print(freecadObjects)
							for obj in freecadObjects:
								#BOUNDING BOX
								bbCoords = obj.Shape.BoundBox

								#PLACEMENT BOX
								print(obj.Placement)
								#print(dir(obj.Placement.Rotation.Axis))
								axisX = obj.Placement.Rotation.Axis.x
								axisY = obj.Placement.Rotation.Axis.y
								axisZ = obj.Placement.Rotation.Axis.z

								#
								# PORT openEMS GENERATION INTO VARIABLE
								#
								if (currSetting.getType() == 'lumped'):
									genScript += 'portStart = [' + str(bbCoords.XMin) + ', ' + str(bbCoords.YMin) + ', ' + str(bbCoords.ZMin) + '];\n'
									genScript += 'portStop = [' + str(bbCoords.XMax) + ', ' + str(bbCoords.YMax) + ', ' + str(bbCoords.ZMax) + '];\n'
									genScript += 'portR = ' + str(currSetting.R) + ';\n'
									genScript += 'portUnits = ' + str(currSetting.getRUnits()) + ';\n'
									genScript += 'portDirection = [' + str(axisX) + ' ' + str(axisY) + ' ' + str(axisZ) + '];\n'

									genScript_isActive = ""
									if (currSetting.isActive in ('True', 'true', '1', 'yes')):
										genScript_isActive = " , true"

									genScript += '[CSX port{' + str(genScriptPortCount) + '}] = AddLumpedPort(CSX, 5, ' + str(genScriptPortCount) + ', portR*portUnits, portStart, portStop, portDirection' + genScript_isActive + ');\n'

									genScriptPortCount += 1
								elif (currSetting.getType() == 'microstrip'):
									genScript += "%% AddMSLPort(CSX, 5 ,1 , 'microstrip', p1.stop, p1.start,'x', [0 0 sourceEz], 'ExcitePort',true, 'Feed_R',p1.R);\n"
								elif (currSetting.getType() == 'circular waveguide'):
									genScript += "%% circular port openEMS code should be here\n"
								elif (currSetting.getType() == 'rectangular waveguide'):
									genScript += "%% rectangular port openEMS code should be here\n"
								elif (currSetting.getType() == 'et dump'):
									genScript += "CSX = AddDump( CSX, '" + currSetting.name + "', 'DumpType', 0, 'DumpMode', 2);\n"
									genScript += 'dumpStart = [' + str(bbCoords.XMin) + ', ' + str(bbCoords.YMin) + ', ' + str(bbCoords.ZMin) + '];\n'
									genScript += 'dumpStop = [' + str(bbCoords.XMax) + ', ' + str(bbCoords.YMax) + ', ' + str(bbCoords.ZMax) + '];\n'
									genScript += "CSX = AddBox( CSX, '" + currSetting.name + "', 0, dumpStart, dumpStop );\n"
								elif (currSetting.getType() == 'ht dump'):
									genScript += "CSX = AddDump( CSX, '" + currSetting.name + "', 'DumpType', 1, 'DumpMode', 2);\n"
									genScript += 'dumpStart = [' + str(bbCoords.XMin) + ', ' + str(bbCoords.YMin) + ', ' + str(bbCoords.ZMin) + '];\n'
									genScript += 'dumpStop = [' + str(bbCoords.XMax) + ', ' + str(bbCoords.YMax) + ', ' + str(bbCoords.ZMax) + '];\n'
									genScript += "CSX = AddBox( CSX, '" + currSetting.name + "', 0, dumpStart, dumpStop );\n"
								else:
									genScript += '% Unknown port type. Nothing was generated. \n'

					#
					#	GRID SETTINGS
					#   _____ _____  _____ _____                                    _           _                 _      
					#  / ____|  __ \|_   _|  __ \                                  | |         | |               | |     
					# | |  __| |__) | | | | |  | |   __ _  ___ _ __   ___ _ __ __ _| |_ ___  __| |   ___ ___   __| | ___ 
					# | | |_ |  _  /  | | | |  | |  / _` |/ _ \ '_ \ / _ \ '__/ _` | __/ _ \/ _` |  / __/ _ \ / _` |/ _ \
					# | |__| | | \ \ _| |_| |__| | | (_| |  __/ | | |  __/ | | (_| | ||  __/ (_| | | (_| (_) | (_| |  __/
					#  \_____|_|  \_\_____|_____/   \__, |\___|_| |_|\___|_|  \__,_|\__\___|\__,_|  \___\___/ \__,_|\___|
					#                                __/ |                                                               
					#                               |___/                                                                
					#
					elif (itemData.__class__.__name__ is "GridSettingsItem"):
						print("Grid Settings detected")
						currentObjects = App.ActiveDocument.Objects						
						if (str(item.parent().text(0)) == "Grid"):
							print("Current item is GRID setting")
							currSetting = item.data(0, QtCore.Qt.UserRole)

							#
							# OCTAVE SCRIPT GOES HERE...
							#
							print("#")
							print("#GRID " + currSetting.getType())
							print("#name " + currSetting.getName())
							print("#")
							if (currSetting.getType() == "Fixed Count"):
								print("#--> x: " + str(currSetting.getXYZ()['x']))
								print("#--> y: " + str(currSetting.getXYZ()['y']))
								print("#--> z: " + str(currSetting.getXYZ()['z']))
							if (currSetting.getType() == "Fixed Distance"):
								print("#--> x: " + str(currSetting.getXYZ()['x']))
								print("#--> y: " + str(currSetting.getXYZ()['y']))
								print("#--> z: " + str(currSetting.getXYZ()['z']))
							if (currSetting.getType() == "User Defined"):
								print("#--> userDefined: " + str(currSetting.getXYZ()))
							print("#--> units: " + str(currSetting.units))
							print("#")

							objs = FreeCAD.ActiveDocument.Objects
							objsExport = []

							#item = current GRID ITEM
							for k in range(item.childCount()):
								childName = item.child(k).text(0)
								print("##Children:")
								print("\t" + childName)
								freecadObjects = [i for i in objs if (i.Label) == childName] 

								#print(freecadObjects)
								for obj in freecadObjects:
									# obj = FreeCAD Object class

									#print('\t--> ' + str(dir(obj.Placement.Base)))
									#print('\t--> x: ' + str(obj.Placement.Base.x))
									#print('\t--> y: ' + str(obj.Placement.Base.y))
									#print('\t--> z: ' + str(obj.Placement.Base.z))

									#BOUNDING BOX
									bbCoords = obj.Shape.BoundBox
									#print(type(bbCoords))
									#print(str(dir(bbCoords)))
									print('\t--> Xlength: ' + str(bbCoords.XLength))
									print('\t--> Ylength: ' + str(bbCoords.YLength))
									print('\t--> Zlength: ' + str(bbCoords.ZLength))
									print('\t--> XMin: ' + str(bbCoords.XMin) + " XMax: " + str(bbCoords.XMax))
									print('\t--> YMin: ' + str(bbCoords.YMin) + " YMax: " + str(bbCoords.YMax))
									print('\t--> ZMin: ' + str(bbCoords.ZMin) + " ZMax: " + str(bbCoords.ZMax))

									#PLACEMENT BOX
									print(obj.Placement)
									#print(dir(obj.Placement.Base))
									offsetX = 0
									offsetY = 0
									offsetZ = 0

									#COORDS ARE GETTING FROM BOUNDING BOX SO THERE SHOULDN'T BE NEEDET TO ADD OFFSET?

									"""
									if (obj.Placement):
										offsetX += obj.Placement.Base.x
										offsetY += obj.Placement.Base.y
										offsetZ += obj.Placement.Base.z
									"""

									#print("\tplacement X: " + str(offsetX))
									#print("\tplacement Y: " + str(offsetY))
									#print("\tplacement Z: " + str(offsetZ))

									#
									# GRID openEMS GENERATION INTO VARIABLE
									#
									genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"
									genScript += "% MESH - " + currSetting.getName() + " - " + childName + "\n"
									genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"
									if (currSetting.getType() == 'Fixed Distance'):
										#UNIT FOR MESH										
										genScript += "mesh.x = [mesh.x (" + str(bbCoords.XMin) + ":" + str(currSetting.getXYZ()['x']) + ":" + str(bbCoords.XMax) + ") + " + str(offsetX) + "];\n"
										genScript += "mesh.y = [mesh.y (" + str(bbCoords.YMin) + ":" + str(currSetting.getXYZ()['y']) + ":" + str(bbCoords.YMax) + ") + " + str(offsetY) + "];\n"
										genScript += "mesh.z = [mesh.z (" + str(bbCoords.ZMin) + ":" + str(currSetting.getXYZ()['z']) + ":" + str(bbCoords.ZMax) + ") + " + str(offsetZ) + "];\n"
										genScript += "CSX = DefineRectGrid(CSX, " + currSetting.getUnitAsScriptLine() + ", mesh);\n"
										pass
									elif (currSetting.getType() == 'Fixed Count'):
										#if just one line is defined then is place in middle										
										if (currSetting.xenabled):
											if (not currSetting.getXYZ()['x'] == 1):
												genScript += "mesh.x = [mesh.x linspace(" + str(bbCoords.XMin) + "," + str(bbCoords.XMax) + "," + str(currSetting.getXYZ()['x']) + ") + " + str(offsetX) + "];\n"
											else:
												genScript += "mesh.x = [mesh.x " + str((bbCoords.XMin + bbCoords.XMax)/2) + " + " + str(offsetX) + "];\n"

										if (currSetting.yenabled):
											if (not currSetting.getXYZ()['y'] == 1):
												genScript += "mesh.y = [mesh.y linspace(" + str(bbCoords.YMin) + "," + str(bbCoords.YMax) + "," + str(currSetting.getXYZ()['y']) + ") + " + str(offsetY) + "];\n"
											else:
												genScript += "mesh.y = [mesh.y " + str((bbCoords.YMin + bbCoords.YMax)/2) + " + " + str(offsetY) + "];\n"

										if (currSetting.zenabled):
											if (not currSetting.getXYZ()['z'] == 1):
												genScript += "mesh.z = [mesh.z linspace(" + str(bbCoords.ZMin) + "," + str(bbCoords.ZMax) + "," + str(currSetting.getXYZ()['z']) + ") + " + str(offsetZ) + "];\n"
											else:
												genScript += "mesh.z = [mesh.z " + str((bbCoords.ZMin + bbCoords.ZMax)/2) + " + " + str(offsetZ) + "];\n"

										genScript += "CSX = DefineRectGrid(CSX, " + currSetting.getUnitAsScriptLine() + ", mesh);\n"
										pass
									elif (currSetting.getType() == 'User Defined'):
										#UNIT FOR MESH										
										genScript += "meshUnit = " + currSetting.getUnitAsScriptLine() + "; % all length in mm\n"
										genScript += "mesh = " + currSetting.getXYZ() + ";\n"
										genScript += "CSX = DefineRectGrid(CSX, " + currSetting.getUnitAsScriptLine() + ", mesh);\n"
										pass

							pass

					#
					# MATERIALS
					#  __  __       _______ ______ _____  _____          _                                        _           _                 _      
					# |  \/  |   /\|__   __|  ____|  __ \|_   _|   /\   | |                                      | |         | |               | |     
					# | \  / |  /  \  | |  | |__  | |__) | | |    /  \  | |        __ _  ___ _ __   ___ _ __ __ _| |_ ___  __| |   ___ ___   __| | ___ 
					# | |\/| | / /\ \ | |  |  __| |  _  /  | |   / /\ \ | |       / _` |/ _ \ '_ \ / _ \ '__/ _` | __/ _ \/ _` |  / __/ _ \ / _` |/ _ \
					# | |  | |/ ____ \| |  | |____| | \ \ _| |_ / ____ \| |____  | (_| |  __/ | | |  __/ | | (_| | ||  __/ (_| | | (_| (_) | (_| |  __/
					# |_|  |_/_/    \_\_|  |______|_|  \_\_____/_/    \_\______|  \__, |\___|_| |_|\___|_|  \__,_|\__\___|\__,_|  \___\___/ \__,_|\___|
					#                                                              __/ |                                                               
					#                                                             |___/                                                               					#                                                                                                                                                                                                                                         
					elif (itemData.__class__.__name__ is "MaterialSettingsItem"):
						currSetting = item.data(0, QtCore.Qt.UserRole)
						print(currSetting)
						if (currSetting.getName() != 'Material Default'):
							print("#")
							print("#MATERIAL")
							print("#name: " + currSetting.getName())
							print("#epsilon, mue, kappa, sigma")
							print("#" + str(currSetting.constants['epsilon']) + ", " + str(currSetting.constants['mue']) + ", " + str(currSetting.constants['kappa']) + ", " + str(currSetting.constants['sigma']))

							genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"
							genScript += "% MATERIAL - " + currSetting.getName() + "\n"
							genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"

							#when material metal use just AddMetal for simulator
							if (currSetting.type == 'metal'):
								genScript += "CSX = AddMetal( CSX, '" + currSetting.getName() + "' );\n"
							elif (currSetting.type == 'userdefined'):
								genScript += "CSX = AddMaterial( CSX, '" + currSetting.getName() + "' );\n"

								#full material definition all 4 params epsilon, mue, kappa and sigma							
								#genScript += "CSX = SetMaterialProperty( CSX, '" + currSetting.getName() + "', 'Epsilon', " + str(currSetting.constants['epsilon']) + ", 'Mue', " + str(currSetting.constants['mue']) + ", 'Kappa', " + str(currSetting.constants['kappa']) + ", 'Sigma', " + str(currSetting.constants['sigma']) + ");\n"
	
								#this is running now, just epsilon and kappa generated
								genScript += "CSX = SetMaterialProperty( CSX, '" + currSetting.getName() + "', 'Epsilon', " + str(currSetting.constants['epsilon']) + ", 'Kappa', " + str(currSetting.constants['kappa']) + ");\n"

							#item = current MATERIAL ITEM
							for k in range(item.childCount()):
								childName = item.child(k).text(0)
								print("##Children:")
								print("\t" + childName)

								currDir, baseName = self.getCurrDir()
								stlModelFileName = childName + "_gen_model.stl"
								genScript += "CSX = ImportSTL(CSX, '" + currSetting.getName() + "',10, [currDir '/" + stlModelFileName + "'],'Transform',{'Scale', 1});\n"

								#   _____ _______ _                                        _   _             
								#  / ____|__   __| |                                      | | (_)            
								# | (___    | |  | |        __ _  ___ _ __   ___ _ __ __ _| |_ _  ___  _ __  
								#  \___ \   | |  | |       / _` |/ _ \ '_ \ / _ \ '__/ _` | __| |/ _ \| '_ \ 
								#  ____) |  | |  | |____  | (_| |  __/ | | |  __/ | | (_| | |_| | (_) | | | |
								# |_____/   |_|  |______|  \__, |\___|_| |_|\___|_|  \__,_|\__|_|\___/|_| |_|
								#                           __/ |                                            
								#                          |___/                                            
								#
								#going through each concrete material items and generate their .stl files
								partToExport = [i for i in FreeCAD.ActiveDocument.Objects if (i.Label) == childName] 
								currDir = os.path.dirname(App.ActiveDocument.FileName)
								exportFileName = currDir + "/" + stlModelFileName
								Mesh.export(partToExport,exportFileName)
								print("Material object exported as STL into: " + stlModelFileName)

						else:
							print("#Material Default")
							print("---")

						pass

					#
					#	 FreeCAD item detection everywhere in Main Tree!!! need to get rid this, now it's tolerated during development!
					#
					#  ______              _____          _____    _ _                   _                    
					# |  ____|            / ____|   /\   |  __ \  (_) |                 | |                   
					# | |__ _ __ ___  ___| |       /  \  | |  | |  _| |_ ___ _ __ ___   | |_ _   _ _ __   ___ 
					# |  __| '__/ _ \/ _ \ |      / /\ \ | |  | | | | __/ _ \ '_ ` _ \  | __| | | | '_ \ / _ \
					# | |  | | |  __/  __/ |____ / ____ \| |__| | | | ||  __/ | | | | | | |_| |_| | |_) |  __/
					# |_|  |_|  \___|\___|\_____/_/    \_\_____/  |_|\__\___|_| |_| |_|  \__|\__, | .__/ \___|
					#                                                                         __/ | |         
					#                                                                        |___/|_|        
					#
					elif (itemData.__class__.__name__ is "FreeCADSettingsItem"):
						print("FreeCAD Settings detected")

						#
						#	GET PARENT NODE DATATYPE
						#
						print("#")
						print("#FREECAD OBJ.")
						if (str(item.parent().text(0)) == "Grid"):
							print("name: Grid Default")
							print("type: FreeCADSettingsItem")
							pass
						elif (str(item.parent().text(0)) == "Ports"):
							print("name: Port Default")
							print("type: FreeCADSettingsItem")
							pass
						elif (str(item.parent().text(0)) == "Excitation"):
							print("name: Excitation Default")
							print("type: FreeCADSettingsItem")
							pass
						elif (str(item.parent().text(0)) == "Materials"):
							print("name: Material Default")
							print("type: FreeCADSettingsItem")
							pass
						else:
							print("Parent of FreeCADSettingItem UNKNOWN")
							pass

						pass
					#  _     _    _ __  __ _____  ______ _____    _____        _____ _______ 
					# | |   | |  | |  \/  |  __ \|  ____|  __ \  |  __ \ /\   |  __ \__   __|
					# | |   | |  | | \  / | |__) | |__  | |  | | | |__) /  \  | |__) | | |   
					# | |   | |  | | |\/| |  ___/|  __| | |  | | |  ___/ /\ \ |  _  /  | |   
					# | |___| |__| | |  | | |    | |____| |__| | | |  / ____ \| | \ \  | |   
					# |______\____/|_|  |_|_|    |______|_____/  |_| /_/    \_\_|  \_\ |_|   
					#                                                                        
					elif (itemData.__class__.__name__ is "LumpedPartSettingsItem"):
						print("LumpedPart Settings detected")
						genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"
						genScript += "% LUMPED PART " + currSetting.getName() + "\n"
						genScript += "%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%%\n"

						#read current category settings
						currentSetting = item.data(0, QtCore.Qt.UserRole)

						#traverse through all children item for this particular lumped part settings
						objs = FreeCAD.ActiveDocument.Objects
						objsExport = []
						for k in range(item.childCount()):
							childName = item.child(k).text(0)
							print("#")
							print("#LUMPED PART " + currentSetting.getType())
							print("#name " + currentSetting.getName())
							print("#")

							freecadObjects = [i for i in objs if (i.Label) == childName] 
							for obj in freecadObjects:
								# obj = FreeCAD Object class

								#BOUNDING BOX
								bbCoords = obj.Shape.BoundBox

								#PLACEMENT BOX
								print(obj.Placement)

								genScript += 'lumpedPartStart = [' + str(bbCoords.XMin) + ', ' + str(bbCoords.YMin) + ', ' + str(bbCoords.ZMin) + ']\n'
								genScript += 'lumpedPartStop = [' + str(bbCoords.XMax) + ', ' + str(bbCoords.YMax) + ', ' + str(bbCoords.ZMax) + ']\n'

								lumpedPartName = currentSetting.name
								lumpedPartParams = ''
								if ('r' in currentSetting.getType().lower()):
									lumpedPartParams += ",'R', " + str(currentSetting.getR())
								if ('l' in currentSetting.getType().lower()):
									lumpedPartParams += ",'L', " + str(currentSetting.getL())
								if ('c' in currentSetting.getType().lower()):
									lumpedPartParams += ",'C', " + str(currentSetting.getC())
								lumpedPartParams = lumpedPartParams.strip(',')

								#WARNING: Caps param has hardwired value 1, will be generated small metal caps to connect part with circuit !!!
								genScript += "[CSX] = AddLumpedElement(CSX, '" + lumpedPartName + "', 2, 'Caps', 1, " + lumpedPartParams + ");\n"
								genScript += "[CSX] = AddBox(CSX, '" + lumpedPartName + "', 0, lumpedPartStart, lumpedPartStop);\n"



						pass

					#  _____ _______ ______ __  __   _    _ _   _ _  ___   _  ______          ___   _ 
					# |_   _|__   __|  ____|  \/  | | |  | | \ | | |/ / \ | |/ __ \ \        / / \ | |
					#   | |    | |  | |__  | \  / | | |  | |  \| | ' /|  \| | |  | \ \  /\  / /|  \| |
					#   | |    | |  |  __| | |\/| | | |  | | . ` |  < | . ` | |  | |\ \/  \/ / | . ` |
					#  _| |_   | |  | |____| |  | | | |__| | |\  | . \| |\  | |__| | \  /\  /  | |\  |
					# |_____|  |_|  |______|_|  |_|  \____/|_| \_|_|\_\_| \_|\____/   \/  \/   |_| \_|
					#                                                                                                          
					else:
						print("unknown: " + itemData.__class__.__name__ + "\n")
						pass
				else:
					print("Object has no UserRole data inside defined")
					pass
				print("\n")

		print("======================== REPORT END ========================\n")

		#
		# WRITE GENERATED SCRIPT INTO FILE
		#
		genScript += "WriteOpenEMS( [Sim_Path '/' Sim_CSX], FDTD, CSX );\n"
		genScript += "CSXGeomPlot( [Sim_Path '/' Sim_CSX] );\n"
		genScript += "\n"
		genScript += "if (postprocessing_only==0)\n"
		genScript += "    %% run openEMS\n"
		genScript += "    RunOpenEMS( Sim_Path, Sim_CSX, openEMS_opts );\n"
		genScript += "end\n"

		#
		# WRITE OpenEMS Script file into current dir
		#
		currDir, nameBase = self.getCurrDir()
		fileName = nameBase + "_openEMS.m"
		f = open(fileName, "w")
		f.write(genScript)
		f.close()
		print('Simulation file written into: ' + fileName)

		return

	def show(self):
		self.form.show()

	def onMoveLeft(self):
		print("Button << clicked.")
		rightItem = self.form.objectAssignmentRightTreeWidget.selectedItems()[0]
		rightItem.parent().removeChild(rightItem)
		return

	def onMoveRight(self):
		print("Button >> clicked.")
		leftItem = self.form.objectAssignmentLeftTreeWidget.selectedItems()[0].clone()
		rightItem = self.form.objectAssignmentRightTreeWidget.selectedItems()[0]

		#check if item is type of SettingsItem based on its class name and if yes then add subitems into it
		reResult = re.search("__main__.(.*)SettingsItem", str(type(rightItem.data(0, QtCore.Qt.UserRole))))
		if (reResult):
			if (reResult.group(1).lower() == 'excitation'):
				self.displayMessage("Excitation doesn't accept any objects.")
				return
			if (reResult.group(1).lower() == 'freecad'):
				self.displayMessage("FreeCAD object cannot have child item.")
				return
			else:
				print("Item ")
				print(leftItem.text(0))
				print("added into ")
				print(rightItem.text(0))
	
			rightItem.addChild(leftItem)
		else:
				self.displayMessage("Item must be added into some settings inside category.")

		"""
		print("Item ")
		print(leftItem.text(0))
		print("added into ")
		print(rightItem.text(0))
		rightItem.addChild(leftItem)
		"""	


	def displayMessage(self, msgText):
		msgBox = QtGui.QMessageBox()
		msgBox.setText(msgText)
		msgBox.exec()

	def checkTreeWidgetForDupliciyName(self,refTreeWidget, itemName):
		isDuplicityName = False
		iterator = QtGui.QTreeWidgetItemIterator(refTreeWidget, QtGui.QTreeWidgetItemIterator.All)
		while iterator.value():
			item = iterator.value()
			if item.text(0) == itemName:
				isDuplicityName = True
				self.displayMessage("Please change name, item with this name already exists.")
			iterator +=1
		return isDuplicityName

	#this should erase all items from tree widgets and everything before loading new configuration to everything pass right
	#	tree widget is just important to erase because all items contains userdata items which contains its configuration and whole
	#	gui is generating code based on these information, so when items are erased and new ones created everything is ok
	def deleteAllSettings(self):
		self.form.objectAssignmentRightTreeWidget.clear()		#init right column as at startup to have default structure cleared
		self.initRightColumnTopLevelItems()					#rerecreate default simulation structure

		self.form.gridSettingsTreeView.clear()				#delete GRID setting
		self.form.materialSettingsTreeView.clear()			#delete MATERIAL setting
		self.form.portSettingsTreeView.clear()				#delete PORT setting
		self.form.excitationSettingsTreeView.clear()			#delete EXCITATION setting
		return

	# GRID SETTINGS
	#   _____ _____  _____ _____     _____ ______ _______ _______ _____ _   _  _____  _____ 
	#  / ____|  __ \|_   _|  __ \   / ____|  ____|__   __|__   __|_   _| \ | |/ ____|/ ____|
	# | |  __| |__) | | | | |  | | | (___ | |__     | |     | |    | | |  \| | |  __| (___  
	# | | |_ |  _  /  | | | |  | |  \___ \|  __|    | |     | |    | | | . ` | | |_ |\___ \ 
	# | |__| | | \ \ _| |_| |__| |  ____) | |____   | |     | |   _| |_| |\  | |__| |____) |
	#  \_____|_|  \_\_____|_____/  |_____/|______|  |_|     |_|  |_____|_| \_|\_____|_____/ 
	#
	def fixedCountRadioButtonClicked(self):
		self.form.userDefinedGridLinesTextInput.setEnabled(False)

	def fixedDistanceRadioButtonClicked(self):
		self.form.userDefinedGridLinesTextInput.setEnabled(False)

	def userDefinedRadioButtonClicked(self):
		self.form.userDefinedGridLinesTextInput.setEnabled(True)

	def getGridItemFromGui(self):
		name = self.form.gridSettingsNameInput.text()
		gridType = ""
		gridX = 0
		gridY = 0
		gridZ = 0
		gridUnits = ""
		gridUserDefined = ""

		gridItem = GridSettingsItem()
		gridItem.name = name

		xenabled = self.form.gridXEnable.isChecked()
		yenabled = self.form.gridYEnable.isChecked()
		zenabled = self.form.gridZEnable.isChecked()
		gridItem.xenabled = xenabled
		gridItem.yenabled = yenabled
		gridItem.zenabled = zenabled

		if (self.form.fixedCountRadioButton.isChecked()):
			gridType = "Fixed Count"
			gridX = self.form.fixedCountXNumberInput.value()
			gridY = self.form.fixedCountYNumberInput.value()
			gridZ = self.form.fixedCountZNumberInput.value()

			gridItem.type = gridType
			gridItem.fixedCount = {}
			gridItem.fixedCount['x'] = gridX
			gridItem.fixedCount['y'] = gridY
			gridItem.fixedCount['z'] = gridZ

			print("---> Saved GridSetting ")
			print(str(gridX) + " " + str(gridY) + " " + str(gridZ))

		if (self.form.fixedDistanceRadioButton.isChecked()):
			gridType = "Fixed Distance"
			gridX = self.form.fixedDistanceXNumberInput.value()
			gridY = self.form.fixedDistanceYNumberInput.value()
			gridZ = self.form.fixedDistanceZNumberInput.value()

			gridItem.type = gridType
			gridItem.fixedDistance = {}
			gridItem.fixedDistance['x'] = gridX
			gridItem.fixedDistance['y'] = gridY
			gridItem.fixedDistance['z'] = gridZ

		if (self.form.userDefinedRadioButton.isChecked()):
			gridType = "User Defined"
			gridUserDefined = self.form.userDefinedGridLinesTextInput.toPlainText()

			gridItem.type = gridType
			gridItem.userDefined = gridUserDefined

		gridItem.units = self.form.gridUnitsInput.currentText()
		return gridItem

	def gridSettingsAddButtonClicked(self):		
		gridItem = self.getGridItemFromGui()

		#check for duplicity in names if there is some warning message displayed
		isDuplicityName = self.checkTreeWidgetForDupliciyName(self.form.gridSettingsTreeView, gridItem.name)

		#if everything is OK, item is added into tree
		if (not isDuplicityName):
			self.addSettingsItemGui(gridItem)

	def gridSettingsRemoveButtonClicked(self):
		#selectedItem = self.form.gridSettingsTreeView.selectedItems()[0].data(0, QtCore.Qt.UserRole)
		#self.displayMessage(selectedItem.serializeToString())

		selectedItem = self.form.gridSettingsTreeView.selectedItems()[0]
		print("Selected port name: " + selectedItem.text(0))

		gridGroupWidgetItems = self.form.objectAssignmentRightTreeWidget.findItems(selectedItem.text(0), QtCore.Qt.MatchExactly|QtCore.Qt.MatchFlag.MatchRecursive)
		gridGroupItem = None
		for item in gridGroupWidgetItems:
			if (item.parent().text(0) == "Grid"):
				gridGroupItem = item
		print("Currently removing port item: " + gridGroupItem.text(0))

		self.form.portSettingsTreeView.invisibleRootItem().removeChild(selectedItem)
		gridGroupItem.parent().removeChild(gridGroupItem)

		return

	def gridSettingsRewriteButtonClicked(self):
		gridSetting = self.getGridItemFromGui()

		selectedItem = self.form.gridSettingsTreeView.selectedItems()[0]
		selectedItem.setData(0, QtCore.Qt.UserRole, gridSetting)

		gridGroupWidgetItems = self.form.objectAssignmentRightTreeWidget.findItems(selectedItem.text(0), QtCore.Qt.MatchExactly|QtCore.Qt.MatchFlag.MatchRecursive)
		gridGroupItem = None
		for item in gridGroupWidgetItems:
			if (item.parent().text(0) == "Grid"):
				item.setData(0, QtCore.Qt.UserRole, gridSetting)

	#
	# MATERIAL SETTINGS
	#  __  __       _______ ______ _____  _____          _         _____ ______ _______ _______ _____ _   _  _____  _____ 
	# |  \/  |   /\|__   __|  ____|  __ \|_   _|   /\   | |       / ____|  ____|__   __|__   __|_   _| \ | |/ ____|/ ____|
	# | \  / |  /  \  | |  | |__  | |__) | | |    /  \  | |      | (___ | |__     | |     | |    | | |  \| | |  __| (___  
	# | |\/| | / /\ \ | |  |  __| |  _  /  | |   / /\ \ | |       \___ \|  __|    | |     | |    | | | . ` | | |_ |\___ \ 
	# | |  | |/ ____ \| |  | |____| | \ \ _| |_ / ____ \| |____   ____) | |____   | |     | |   _| |_| |\  | |__| |____) |
	# |_|  |_/_/    \_\_|  |______|_|  \_\_____/_/    \_\______| |_____/|______|  |_|     |_|  |_____|_| \_|\_____|_____/ 
	#                                                                                                                     
	def materialSettingsAddButtonClicked(self):
		name = self.form.materialSettingsNameInput.text()
		epsilon = self.form.materialEpsilonNumberInput.value()
		mue = self.form.materialMueNumberInput.value()
		kappa = self.form.materialKappaNumberInput.value()
		sigma = self.form.materialSigmaNumberInput.value()
		
		materialItem = MaterialSettingsItem()
		materialItem.name = name
		materialItem.constants = {}	# !!! <--- THIS MUST BE HERE, OTHERWISE ALL CONSTANTS IN ALL MATERIAL ITEMS HAVE SAME VALUE LIKE REFERENCING SAME OBJECT
		materialItem.constants['epsilon'] = epsilon
		materialItem.constants['mue'] = mue
		materialItem.constants['kappa'] = kappa
		materialItem.constants['sigma'] = sigma	

		if (self.form.materialMetalRadioButton.isChecked() == 1):
			materialItem.type = "metal"
		elif (self.form.materialUserDefinedRadioButton.isChecked() == 1):
			materialItem.type = "userdefined"

		# display message box with current material settings to be added
		#self.displayMessage(materialItem.serializeToString())

		#check for duplicity in names if there is some warning message displayed
		isDuplicityName = self.checkTreeWidgetForDupliciyName(self.form.materialSettingsTreeView, materialItem.name)

		if (not isDuplicityName):
			self.addSettingsItemGui(materialItem)

	def materialSettingsRemoveButtonClicked(self):
		selectedItem = self.form.materialSettingsTreeView.selectedItems()[0]
		print("Selected material name: " + selectedItem.text(0))

		materialGroupWidgetItems = self.form.objectAssignmentRightTreeWidget.findItems(selectedItem.text(0), QtCore.Qt.MatchExactly|QtCore.Qt.MatchFlag.MatchRecursive)
		materialGroupItem = None
		for item in materialGroupWidgetItems:
			if (item.parent().text(0) == "Material"):
				materialGroupItem = item
		print("Currently removing material item: " + materialGroupItem.text(0))

		self.form.materialSettingsTreeView.invisibleRootItem().removeChild(selectedItem)
		materialGroupItem.parent().removeChild(materialGroupItem)

		return

	# EXCITATION SETTINGS
	#  ________   _______ _____ _______    _______ _____ ____  _   _    _____ ______ _______ _______ _____ _   _  _____  _____ 
	# |  ____\ \ / / ____|_   _|__   __|/\|__   __|_   _/ __ \| \ | |  / ____|  ____|__   __|__   __|_   _| \ | |/ ____|/ ____|
	# | |__   \ V / |      | |    | |  /  \  | |    | || |  | |  \| | | (___ | |__     | |     | |    | | |  \| | |  __| (___  
	# |  __|   > <| |      | |    | | / /\ \ | |    | || |  | | . ` |  \___ \|  __|    | |     | |    | | | . ` | | |_ |\___ \ 
	# | |____ / . \ |____ _| |_   | |/ ____ \| |   _| || |__| | |\  |  ____) | |____   | |     | |   _| |_| |\  | |__| |____) |
	# |______/_/ \_\_____|_____|  |_/_/    \_\_|  |_____\____/|_| \_| |_____/|______|  |_|     |_|  |_____|_| \_|\_____|_____/ 
	#                                                                                                                          

	def excitationSettingsAddButtonClicked(self):
		name = self.form.excitationSettingsNameInput.text()

		excitationItem = ExcitationSettingsItem()
		excitationItem.name = name
		excitationItem.units = self.form.excitationUnitsNumberInput.currentText()

		if (self.form.sinusodialExcitationRadioButton.isChecked()):
			excitationItem.type = 'sinusodial'
			excitationItem.sinusodial = {}
			excitationItem.sinusodial['fc'] = self.form.sinusodialExcitationFcNumberInput.value()
		if (self.form.gaussianExcitationRadioButton.isChecked()):
			excitationItem.type = 'gaussian'
			excitationItem.gaussian = {}
			excitationItem.gaussian['fc'] = self.form.gaussianExcitationFcNumberInput.value()
			excitationItem.gaussian['f0'] = self.form.gaussianExcitationF0NumberInput.value()
		if (self.form.customExcitationRadioButton.isChecked()):
			excitationItem.type = 'custom'
			excitationItem.custom = {}
			excitationItem.custom['functionStr'] = self.form.customExcitationTextInput.text()

		#check for duplicity in names if there is some warning message displayed
		isDuplicityName = self.checkTreeWidgetForDupliciyName(self.form.excitationSettingsTreeView, excitationItem.name)
		isMoreThanOne = self.form.excitationSettingsTreeView.topLevelItemCount() > 0

		if (isDuplicityName):
			return
		if (isMoreThanOne):
			self.displayMessage("There could be just one excitation!")
			return
		
		self.addSettingsItemGui(excitationItem)

	def excitationSettingsRemoveButtonClicked(self):
		selectedItem = self.form.excitationSettingsTreeView.selectedItems()[0]
		print("Selected port name: " + selectedItem.text(0))

		excitationGroupWidgetItems = self.form.objectAssignmentRightTreeWidget.findItems(selectedItem.text(0), QtCore.Qt.MatchExactly|QtCore.Qt.MatchFlag.MatchRecursive)
		excitationGroupItem = None
		for item in excitationGroupWidgetItems:
			if (item.parent().text(0) == "Excitation"):
				excitationGroupItem = item
		print("Currently removing port item: " + excitationGroupItem.text(0))

		self.form.excitationSettingsTreeView.invisibleRootItem().removeChild(selectedItem)
		excitationGroupItem.parent().removeChild(excitationGroupItem)

		return

	# PORT SETTINGS
	#  _____   ____  _____ _______    _____ ______ _______ _______ _____ _   _  _____  _____ 
	# |  __ \ / __ \|  __ \__   __|  / ____|  ____|__   __|__   __|_   _| \ | |/ ____|/ ____|
	# | |__) | |  | | |__) | | |    | (___ | |__     | |     | |    | | |  \| | |  __| (___  
	# |  ___/| |  | |  _  /  | |     \___ \|  __|    | |     | |    | | | . ` | | |_ |\___ \ 
	# | |    | |__| | | \ \  | |     ____) | |____   | |     | |   _| |_| |\  | |__| |____) |
	# |_|     \____/|_|  \_\ |_|    |_____/|______|  |_|     |_|  |_____|_| \_|\_____|_____/ 
	#                                                                                        
	def portSettingsAddButtonClicked(self):
		name = self.form.portSettingsNameInput.text()

		portItem = PortSettingsItem()
		portItem.name = name

		if (self.form.lumpedPortRadioButton.isChecked()):
			portItem.type = "lumped"
		if (self.form.microstripPortRadioButton.isChecked()):
			portItem.type = "microstrip"
		if (self.form.circularWaveguidePortRadioButton.isChecked()):
			portItem.type = "circular waveguide"
		if (self.form.rectangularWaveguidePortRadioButton.isChecked()):
			portItem.type = "rectangular waveguide"
		if (self.form.etDumpPortRadioButton.isChecked()):
			portItem.type = "et dump"
		if (self.form.htDumpPortRadioButton.isChecked()):
			portItem.type = "ht dump"

		#check for duplicity in names if there is some warning message displayed
		isDuplicityName = self.checkTreeWidgetForDupliciyName(self.form.portSettingsTreeView, portItem.name)

		if (not isDuplicityName):
			self.addSettingsItemGui(portItem)

		return

	def portSettingsRemoveButtonClicked(self):
		selectedItem = self.form.portSettingsTreeView.selectedItems()[0]
		print("Selected port name: " + selectedItem.text(0))

		portGroupWidgetItems = self.form.objectAssignmentRightTreeWidget.findItems(selectedItem.text(0), QtCore.Qt.MatchExactly|QtCore.Qt.MatchFlag.MatchRecursive)
		portGroupItem = None
		for item in portGroupWidgetItems:
			if (item.parent().text(0) == "Port"):
				portGroupItem = item
		print("Currently removing port item: " + portGroupItem.text(0))

		self.form.portSettingsTreeView.invisibleRootItem().removeChild(selectedItem)
		portGroupItem.parent().removeChild(portGroupItem)

		return


	#  _     _    _ __  __ _____  ______ _____    _____        _____ _______            _   _   _                 
	# | |   | |  | |  \/  |  __ \|  ____|  __ \  |  __ \ /\   |  __ \__   __|          | | | | (_)                
	# | |   | |  | | \  / | |__) | |__  | |  | | | |__) /  \  | |__) | | |     ___  ___| |_| |_ _ _ __   __ _ ___ 
	# | |   | |  | | |\/| |  ___/|  __| | |  | | |  ___/ /\ \ |  _  /  | |    / __|/ _ \ __| __| | '_ \ / _` / __|
	# | |___| |__| | |  | | |    | |____| |__| | | |  / ____ \| | \ \  | |    \__ \  __/ |_| |_| | | | | (_| \__ \
	# |______\____/|_|  |_|_|    |______|_____/  |_| /_/    \_\_|  \_\ |_|    |___/\___|\__|\__|_|_| |_|\__, |___/
	#                                                                                                    __/ |    
	#                                                                                                   |___/    
	#
	def lumpedPartSettingsAddButtonClicked(self):
		name = self.form.lumpedPartSettingsNameInput.text()

		lumpedPartItem = LumpedPartSettingsItem()
		lumpedPartItem.name = name

		if (self.form.lumpedPartLEnable.isChecked()):
			lumpedPartItem.params['L'] = self.form.lumpedPartLInput.value()
			lumpedPartItem.params['LUnits'] = self.form.lumpedPartLUnits.currentText()
			lumpedPartItem.params['LEnabled'] = 1
		if (self.form.lumpedPartREnable.isChecked()):
			lumpedPartItem.params['R'] = self.form.lumpedPartRInput.value()
			lumpedPartItem.params['RUnits'] = self.form.lumpedPartRUnits.currentText()
			lumpedPartItem.params['REnabled'] = 1
		if (self.form.lumpedPartCEnable.isChecked()):
			lumpedPartItem.params['C'] = self.form.lumpedPartCInput.value()
			lumpedPartItem.params['CUnits'] = self.form.lumpedPartCUnits.currentText()
			lumpedPartItem.params['CEnabled'] = 1

		#check for duplicity in names if there is some warning message displayed
		isDuplicityName = self.checkTreeWidgetForDupliciyName(self.form.lumpedPartTreeView, lumpedPartItem.name)
		if (not isDuplicityName):
			self.addSettingsItemGui(lumpedPartItem)

		return

	def lumpedPartSettingsRemoveButtonClicked(self):
		selectedItem = self.form.lumpedPartTreeView.selectedItems()[0]
		print("Selected lumpedpart name: " + selectedItem.text(0))

		lumpedPartGroupWidgetItems = self.form.objectAssignmentRightTreeWidget.findItems(selectedItem.text(0), QtCore.Qt.MatchExactly|QtCore.Qt.MatchFlag.MatchRecursive)
		lumpedPartGroupItem = None
		for item in lumpedPartGroupWidgetItems:
			if (item.parent().text(0).lower() == "lumpedpart"):
				lumpedPartGroupItem = item
		print("Currently removing lumped part item: " + lumpedPartGroupItem.text(0))

		self.form.lumpedPartTreeView.invisibleRootItem().removeChild(selectedItem)
		lumpedPartGroupItem.parent().removeChild(lumpedPartGroupItem)

		return







	#   _____________   ____________  ___    __       _____ _______________________   _____________
	#  / ____/ ____/ | / / ____/ __ \/   |  / /      / ___// ____/_  __/_  __/  _/ | / / ____/ ___/
	# / / __/ __/ /  |/ / __/ / /_/ / /| | / /       \__ \/ __/   / /   / /  / //  |/ / / __ \__ \ 
	#/ /_/ / /___/ /|  / /___/ _, _/ ___ |/ /___    ___/ / /___  / /   / / _/ // /|  / /_/ /___/ / 
	#\____/_____/_/ |_/_____/_/ |_/_/  |_/_____/   /____/_____/ /_/   /_/ /___/_/ |_/\____//____/  
	#
	def materialTreeWidgetItemChanged(self, current, previous):
		print("Material item changed.")
		currSetting = self.form.materialSettingsTreeView.currentItem().data(0, QtCore.Qt.UserRole)
		self.form.materialSettingsNameInput.setText(currSetting.name)

		#ATTENTIONS there is ocnversion to float() used BELOW
		if (currSetting.type == 'metal'):
			self.form.materialMetalRadioButton.click()
		elif (currSetting.type == 'userdefined'):
			self.form.materialUserDefinedRadioButton.click()

		self.form.materialEpsilonNumberInput.setValue(float(currSetting.constants['epsilon']))
		self.form.materialMueNumberInput.setValue(float(currSetting.constants['mue']))
		self.form.materialKappaNumberInput.setValue(float(currSetting.constants['kappa']))
		self.form.materialSigmaNumberInput.setValue(float(currSetting.constants['sigma']))
		return

	def gridTreeWidgetItemChanged(self, current, previous):
		print("Grid item changed.")
		currSetting = self.form.gridSettingsTreeView.currentItem().data(0, QtCore.Qt.UserRole)
		self.form.gridSettingsNameInput.setText(currSetting.name)

		index = self.form.gridUnitsInput.findText(currSetting.units, QtCore.Qt.MatchFixedString)
		if index >= 0:
			self.form.gridUnitsInput.setCurrentIndex(index)

		if (currSetting.type == "Fixed Distance"):
			self.form.fixedDistanceRadioButton.click()
			self.form.fixedDistanceXNumberInput.setValue(currSetting.fixedDistance['x'])
			self.form.fixedDistanceYNumberInput.setValue(currSetting.fixedDistance['y'])
			self.form.fixedDistanceZNumberInput.setValue(currSetting.fixedDistance['z'])
		elif (currSetting.type == "Fixed Count"):
			self.form.fixedCountRadioButton.click()
			self.form.fixedCountXNumberInput.setValue(currSetting.fixedCount['x'])
			self.form.fixedCountYNumberInput.setValue(currSetting.fixedCount['y'])
			self.form.fixedCountZNumberInput.setValue(currSetting.fixedCount['z'])
			pass
		elif (currSetting.type == "User Defined"):
			self.form.userDefinedRadioButton.click()
			self.form.userDefinedGridLinesTextInput.setPlainText(currSetting.userDefined['data'])
			pass
		else:
			pass
			
		self.form.gridXEnable.setChecked(currSetting.xenabled in ('true', 'True', '1', 'yes', True))
		self.form.gridYEnable.setChecked(currSetting.yenabled in ('true', 'True', '1', 'yes', True))
		self.form.gridZEnable.setChecked(currSetting.zenabled in ('true', 'True', '1', 'yes', True))

		return

	def excitationTreeWidgetItemChanged(self, current, previous):
		print("Excitation item changed.")
		currSetting = self.form.excitationSettingsTreeView.currentItem().data(0, QtCore.Qt.UserRole)
		self.form.excitationSettingsNameInput.setText(currSetting.name)
		if (currSetting.type == "sinusodial"):
			self.form.sinusodialExcitationRadioButton.click()
			self.form.sinusodialExcitationFcNumberInput.setValue(currSetting.sinusodial['fc'])
		elif (currSetting.type == "gaussian"):
			self.form.gaussianExcitationRadioButton.click()
			self.form.gaussianExcitationF0NumberInput.setValue(currSetting.gaussian['f0'])
			self.form.gaussianExcitationFcNumberInput.setValue(currSetting.gaussian['fc'])
			pass
		elif (currSetting.type == "custom"):
			self.form.customExcitationRadioButton.click()
			self.form.customExcitationTextInput.setText(currSetting.custom['functionStr'])
			index = self.form.excitationUnitsNumberInput.findText(currSetting.units, QtCore.Qt.MatchFixedString)
			if index >= 0:
				self.form.excitationUnitsNumberInput.setCurrentIndex(index)
			pass
		else:
			return #no gui update
			
		index = self.form.excitationUnitsNumberInput.findText(currSetting.units, QtCore.Qt.MatchFixedString)
		if index >= 0:
			self.form.excitationUnitsNumberInput.setCurrentIndex(index)

		return

	def portTreeWidgetItemChanged(self, current, previous):
		print("Port item changed.")

		currSetting = self.form.portSettingsTreeView.currentItem().data(0, QtCore.Qt.UserRole)
		self.form.portSettingsNameInput.setText(currSetting.name)
		self.form.portResistanceInput.setValue(float(currSetting.R))

		index = self.form.portResistanceUnitsInput.findText(currSetting.RUnits, QtCore.Qt.MatchFixedString)
		if index >= 0:
			self.form.portResistanceUnitsInput.setCurrentIndex(index)

		self.form.portResistanceInput.setEnabled(True)
		self.form.portResistanceUnitsInput.setEnabled(True)

		if (currSetting.type.lower() == "lumped"):
			self.form.lumpedPortRadioButton.click()
			pass
		elif (currSetting.type.lower() == "microstrip"):
			self.form.microstripPortRadioButton.click()
			pass
		elif (currSetting.type.lower() == "circular waveguide"):
			self.form.circularWaveguidePortRadioButton.click()
			pass
		elif (currSetting.type.lower() == "rectangular waveguide"):
			self.form.rectangularWaveguidePortRadioButton.click()
			pass
		elif (currSetting.type.lower() == "et dump"):
			self.form.portResistanceInput.setEnabled(False)
			self.form.portResistanceUnitsInput.setEnabled(False)
			self.form.etDumpPortRadioButton.click()
			pass
		elif (currSetting.type.lower() == "ht dump"):
			self.form.portResistanceInput.setEnabled(False)
			self.form.portResistanceUnitsInput.setEnabled(False)
			self.form.htDumpPortRadioButton.click()
			pass
		else:
			pass #no gui update

		self.form.portActive.setChecked(currSetting.isActive in ('true', 'True', '1', 'yes'))	#convert value from INI file to bool

		return

	def simulationTreeWidgetItemChanged(self, current, previous):
		print("Simulation params changed.")
		return

	def lumpedPartTreeWidgetItemChanged(self, current, previous):
		print("Lumped part item changed.")
		currSetting = self.form.lumpedPartTreeView.currentItem().data(0, QtCore.Qt.UserRole)
		self.form.lumpedPartSettingsNameInput.setText(currSetting.name)

		self.form.lumpedPartLEnable.setChecked(False)
		self.form.lumpedPartREnable.setChecked(False)
		self.form.lumpedPartCEnable.setChecked(False)
		if (currSetting.params['LEnabled']):
			self.form.lumpedPartLEnable.setChecked(True)
		if (currSetting.params['REnabled']):
			self.form.lumpedPartREnable.setChecked(True)
		if (currSetting.params['CEnabled']):
			self.form.lumpedPartCEnable.setChecked(True)

		self.form.lumpedPartLInput.setValue(currSetting.params['L'])
		self.form.lumpedPartRInput.setValue(currSetting.params['R'])
		self.form.lumpedPartCInput.setValue(currSetting.params['C'])

		index = self.form.lumpedPartLUnits.findText(currSetting.params['LUnits'], QtCore.Qt.MatchFixedString)
		if index >= 0:
			self.form.lumpedPartLUnits.setCurrentIndex(index)
		index = self.form.lumpedPartRUnits.findText(currSetting.params['RUnits'], QtCore.Qt.MatchFixedString)
		if index >= 0:
			self.form.lumpedPartRUnits.setCurrentIndex(index)
		index = self.form.lumpedPartCUnits.findText(currSetting.params['CUnits'], QtCore.Qt.MatchFixedString)
		if index >= 0:
			self.form.lumpedPartCUnits.setCurrentIndex(index)

		return

	####################################################################################################################################################################
	# GUI SAVE/LOAD buttons
	####################################################################################################################################################################

	#   _____    __      ________    _____ ______ _______ _______ _____ _   _  _____  _____ 
	#  / ____|  /\ \    / /  ____|  / ____|  ____|__   __|__   __|_   _| \ | |/ ____|/ ____|
	# | (___   /  \ \  / /| |__    | (___ | |__     | |     | |    | | |  \| | |  __| (___  
	#  \___ \ / /\ \ \/ / |  __|    \___ \|  __|    | |     | |    | | | . ` | | |_ |\___ \ 
	#  ____) / ____ \  /  | |____   ____) | |____   | |     | |   _| |_| |\  | |__| |____) |
	# |_____/_/    \_\/   |______| |_____/|______|  |_|     |_|  |_____|_| \_|\_____|_____/ 
	#
	def saveCurrentSettingsButtonClicked(self):
		programname = os.path.basename(App.ActiveDocument.FileName)
		programdir = os.path.dirname(App.ActiveDocument.FileName)
		programbase, ext = os.path.splitext(programname)  # extract basename and ext from filename
		outFile = programdir + '/' + programbase + "_settings.ini"
		print("Saving data from file: " + outFile)

		if (os.path.exists(outFile)):
			os.remove(outFile)	#if there is aready settings file erase to not cause problems with already written objects inside

		settings = QtCore.QSettings(outFile, QtCore.QSettings.IniFormat)    

		#SAE MATERIAL SETTINGS INTO FILE
		materialList = self.openEMSObj.getAllTreeWidgetItems(self.form.materialSettingsTreeView)
		for k in range(len(materialList)):
			print("Save new MATERIAL constants into file: ")
			print(materialList[k].constants)
	
			settings.beginGroup("MATERIAL-" + materialList[k].getName())
			settings.setValue("type", materialList[k].type)
			settings.setValue("material_epsilon", materialList[k].constants['epsilon'])
			settings.setValue("material_mue", materialList[k].constants['mue'])
			settings.setValue("material_kappa", materialList[k].constants['kappa'])
			settings.setValue("material_sigma", materialList[k].constants['sigma'])
			settings.endGroup()

		#SAVE GRID INTO FILE
		gridList = self.openEMSObj.getAllTreeWidgetItems(self.form.gridSettingsTreeView)
		for k in range(len(gridList)):
			print("Save new GRID constants into file: " + gridList[k].getName())
	
			settings.beginGroup("GRID-" + gridList[k].getName())
			settings.setValue("type", gridList[k].type)
			settings.setValue("units", gridList[k].units)
			settings.setValue("xenabled", gridList[k].xenabled)
			settings.setValue("yenabled", gridList[k].yenabled)
			settings.setValue("zenabled", gridList[k].zenabled)
			settings.setValue("fixedCount", json.dumps(gridList[k].fixedCount))
			settings.setValue("fixedDistance", json.dumps(gridList[k].fixedDistance))
			settings.setValue("userDefined", json.dumps(gridList[k].userDefined))
			settings.endGroup()

		#SAVE EXCITATION INTO FILE
		excitationList = self.openEMSObj.getAllTreeWidgetItems(self.form.excitationSettingsTreeView)
		for k in range(len(excitationList)):
			print("Save new EXCITATION constants into file: " + excitationList[k].getName())
	
			settings.beginGroup("EXCITATION-" + excitationList[k].getName())
			settings.setValue("type", excitationList[k].type)
			settings.setValue("sinusodial", json.dumps(excitationList[k].sinusodial))
			settings.setValue("gaussian", json.dumps(excitationList[k].gaussian))
			settings.setValue("custom", json.dumps(excitationList[k].custom))
			settings.setValue("units", excitationList[k].units)
			settings.endGroup()

		#SAVE PORT SETTINGS INTO FILE
		portList = self.openEMSObj.getAllTreeWidgetItems(self.form.portSettingsTreeView)
		for k in range(len(portList)):
			print("Save new PORT constants into file: " + portList[k].getName())
	
			settings.beginGroup("PORT-" + portList[k].getName())
			settings.setValue("type", portList[k].type)
			settings.setValue("R", portList[k].R)
			settings.setValue("RUnits", portList[k].RUnits)
			settings.setValue("isActive", portList[k].isActive)
			settings.endGroup()

		#SIMULATION PARAMS SAVE INTO FILE
		simulationSettings = SimulationSettingsItem("Hardwired Name 1")
		simulationSettings.params['max_timestamps'] = self.form.simParamsMaxTimesteps.value()
		simulationSettings.params['min_decrement'] = self.form.simParamsMinDecrement.value()

		settings.beginGroup("SIMULATION-" + simulationSettings.name)
		settings.setValue("name", simulationSettings.name)
		settings.setValue("params", json.dumps(simulationSettings.params))
		settings.endGroup()


		#SAVE OBJECT ASSIGNMENTS		
		topItemsCount = self.form.objectAssignmentRightTreeWidget.topLevelItemCount()
		objCounter = 0
		for k in range(topItemsCount):
			topItem = self.form.objectAssignmentRightTreeWidget.topLevelItem(k)
			topItemName = topItem.text(0)
			print("---> topItem: " + topItem.text(0))
			for m in range(topItem.childCount()):
				childItem = topItem.child(m)
				childItemName = childItem.text(0)
				print("Save new OBJECT ASSIGNMENTS for catgeroy -> settings profile: ")
				print("\t" + topItemName + " --> " + childItemName)
				for n in range(childItem.childCount()):
					objItem = childItem.child(n)
					objItemName = objItem.text(0)
	
					settings.beginGroup("_OBJECT" + str(objCounter) + "-" + objItemName)
					settings.setValue("type", "FreeCadObj")
					settings.setValue("parent", childItemName)
					settings.setValue("category", topItemName)
					settings.endGroup()

					objCounter += 1

		#SAVE LUMPED PART SETTINGS INTO FILE
		lumpedPartList = self.openEMSObj.getAllTreeWidgetItems(self.form.lumpedPartTreeView)
		print(str(len(lumpedPartList)))
		for k in range(len(lumpedPartList)):
			print("Save new LUMPE PART constants into file: " + lumpedPartList[k].getName())
	
			settings.beginGroup("LUMPEDPART-" + lumpedPartList[k].getName())
			settings.setValue("params", json.dumps(lumpedPartList[k].params))
			settings.endGroup()



		#sys.exit()  # prevents second call
		print("Current values saved into file: " + outFile)
		return

	#  _      ____          _____     _____ ______ _______ _______ _____ _   _  _____  _____ 
	# | |    / __ \   /\   |  __ \   / ____|  ____|__   __|__   __|_   _| \ | |/ ____|/ ____|
	# | |   | |  | | /  \  | |  | | | (___ | |__     | |     | |    | | |  \| | |  __| (___  
	# | |   | |  | |/ /\ \ | |  | |  \___ \|  __|    | |     | |    | | | . ` | | |_ |\___ \ 
	# | |___| |__| / ____ \| |__| |  ____) | |____   | |     | |   _| |_| |\  | |__| |____) |
	# |______\____/_/    \_\_____/  |_____/|______|  |_|     |_|  |_____|_| \_|\_____|_____/ 
	#                                                                                       
	def loadCurrentSettingsButtonClicked(self):
		print("Load current values from file.")

		#FIRST DELETE ALL GUI TREE WIDGET ITEMS
		self.deleteAllSettings()

		#
		# DEBUG: now read hardwired file name with __file__ + "_settings.ini"
		#
		programname = os.path.basename(App.ActiveDocument.FileName)
		programdir = os.path.dirname(App.ActiveDocument.FileName)
		programbase, ext = os.path.splitext(programname)  # extract basename and ext from filename
		outFile = programdir + '/' + programbase + "_settings.ini"
		print("Loading data from file: " + outFile)
		settings = QtCore.QSettings(outFile, QtCore.QSettings.IniFormat)    

		#
		# LOADING ITEMS FROM SETTINGS FILE
		#
		print("Settings file groups:", end="")
		print(settings.childGroups())
		for settingsGroup in settings.childGroups():

			#extract category nme from ini name
			itemNameReg = re.search("-(.*)", settingsGroup)
			itemName = itemNameReg.group(1)

			if (re.compile("EXCITATION").search(settingsGroup)):
				print("Excitation item settings found.")
				settings.beginGroup(settingsGroup)
				categorySettings = ExcitationSettingsItem()
				categorySettings.name = itemName
				categorySettings.type = settings.value('type')
				categorySettings.sinusodial = json.loads(settings.value('sinusodial'))
				categorySettings.gaussian = json.loads(settings.value('gaussian'))
				categorySettings.custom = json.loads(settings.value('custom'))
				categorySettings.units = settings.value('units')
				settings.endGroup()

			elif (re.compile("GRID").search(settingsGroup)):
				print("GRID item settings found.")
				settings.beginGroup(settingsGroup)
				categorySettings = GridSettingsItem()
				categorySettings.name = itemName
				categorySettings.type = settings.value('type')
				categorySettings.xenabled = settings.value('xenabled')
				categorySettings.yenabled = settings.value('yenabled')
				categorySettings.zenabled = settings.value('zenabled')
				categorySettings.units = settings.value('units')
				categorySettings.fixedDistance = json.loads(settings.value('fixedDistance'))
				categorySettings.fixedCount = json.loads(settings.value('fixedCount'))
				categorySettings.userDefined = json.loads(settings.value('userDefined'))
				settings.endGroup()

			elif (re.compile("PORT").search(settingsGroup)):
				print("PORT item settings found.")
				settings.beginGroup(settingsGroup)
				categorySettings = PortSettingsItem()
				categorySettings.name = itemName
				categorySettings.type = settings.value('type')
				categorySettings.R = settings.value('R')
				categorySettings.RUnits = settings.value('RUnits')
				categorySettings.isActive = settings.value('isActive')
				settings.endGroup()

			elif (re.compile("MATERIAL").search(settingsGroup)):
				print("Material item settings found.")
				settings.beginGroup(settingsGroup)
				categorySettings = MaterialSettingsItem()
				categorySettings.name = itemName
				categorySettings.type = settings.value('type')
				categorySettings.constants = {}
				categorySettings.constants['epsilon'] = settings.value('material_epsilon')
				categorySettings.constants['mue'] = settings.value('material_mue')
				categorySettings.constants['kappa'] = settings.value('material_kappa')
				categorySettings.constants['sigma'] = settings.value('material_sigma')
				settings.endGroup()

			elif (re.compile("SIMULATION").search(settingsGroup)):
				print("Simulation params item settings found.")
				settings.beginGroup(settingsGroup)
				simulationSettings = SimulationSettingsItem()
				simulationSettings.name = itemName
				simulationSettings.type = settings.value('type')
				simulationSettings.params = json.loads(settings.value('params'))
				print('SIMULATION PARAMS:')
				print(simulationSettings.params)
				settings.endGroup()

				self.form.simParamsMaxTimesteps.setValue(simulationSettings.params['max_timestamps'])
				self.form.simParamsMinDecrement.setValue(simulationSettings.params['min_decrement'])

				continue	#there is no tree widget to add item to

			elif (re.compile("_OBJECT").search(settingsGroup)):
				print("FreeCadObject item settings found.")
				settings.beginGroup(settingsGroup)
				objParent = settings.value('parent')
				objCategory = settings.value('category')
				print("\t" + objParent)
				print("\t" + objCategory)
				settings.endGroup()

				#adding excitation also into OBJCET ASSIGNMENT WINDOW
				targetGroup = self.form.objectAssignmentRightTreeWidget.findItems(objCategory, QtCore.Qt.MatchExactly)
				print("\t" + str(targetGroup))
				for k in range(len(targetGroup)):					
					print("\t" + targetGroup[k].text(0))
					for m in range(targetGroup[k].childCount()):
						print("\t" + targetGroup[k].child(m).text(0))
						if (targetGroup[k].child(m).text(0) == objParent):
							settingsItem = FreeCADSettingsItem(itemName)

							#treeItem = QtGui.QTreeWidgetItem([itemName])
							treeItem = QtGui.QTreeWidgetItem()
							treeItem.setText(0, itemName)
							treeItem.setIcon(0, QtGui.QIcon(".\\img\\object.png"))
							treeItem.setData(0, QtCore.Qt.UserRole, settingsItem)

							targetGroup[k].child(m).addChild(treeItem)
							print("\tItem added")
							
				continue #items is already added into tree widget nothing more needed

			elif (re.compile("LUMPEDPART").search(settingsGroup)):
				print("LumpedPart item settings found.")
				settings.beginGroup(settingsGroup)
				categorySettings = LumpedPartSettingsItem()
				categorySettings.name = itemName
				categorySettings.params = json.loads(settings.value('params'))
				settings.endGroup()

			else:
				#if no item recognized then conitnue next run, at the end there is adding into object assignment tab
				#and if category is not known it's need to goes for another one
				continue

			self.addSettingsItemGui(categorySettings)		#better more universal way to add things to gui

		self.displayMessage("Settings loaded from file: " + outFile)
		return

####################################################################################################################################################################
# End of PANEL definition
####################################################################################################################################################################
 
panel = BoxTaskPanel()
#FreeCADGui.Control.showDialog(panel)
panel.show()
