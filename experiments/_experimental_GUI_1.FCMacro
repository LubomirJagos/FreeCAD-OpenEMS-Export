# import statements
from PySide import QtGui, QtCore
import re
import os
import copy

class OpenEMS:
	def getOpenEMSObjects():
		currentObjects = App.ActiveDocument.Objects
		
		objToExport = []
		
		for obj in currentObjects:
			if (re.search('openEMS', obj.Label)):
				objToExport.append(obj)
	
		return objToExport

	def getAllObjects():
		currentObjects = App.ActiveDocument.Objects	
		objList = []
		for obj in currentObjects:
			item = QtGui.QTreeWidgetItem([obj.Label])
			item.setIcon(0, QtGui.QIcon(".\\img\\object.png"))
			objList.append(item)
		return objList

# UI Class definitions

class ExampleModalGuiClass(QtGui.QDialog):
	""""""
	def __init__(self):
		super(ExampleModalGuiClass, self).__init__()
		self.initUI()
	def initUI(self):
		self.result = userCancelled
		# create our window
		# define window		xLoc,yLoc,xDim,yDim
		self.setGeometry(250, 250, 1000, 700)
		self.setWindowTitle("Our Example Modal Program Window")
		self.setWindowFlags(QtCore.Qt.WindowStaysOnTopHint)

		#
		# Change current path to script file folder
		#
		abspath = os.path.abspath(__file__)
		dname = os.path.dirname(abspath)
		os.chdir(dname)

		#
		# Main Tab Widget
		#
		self.tabWidget = QtGui.QTabWidget(self)
		self.tabWidget.setGeometry(15,10,960,670)

		self.tab1 = QtGui.QWidget()
		self.tabWidget.addTab(self.tab1, "Objects Assignment")
		self.tab2 = QtGui.QWidget()
		self.tabWidget.addTab(self.tab2, "Grid Settings")
		self.tab3 = QtGui.QWidget()
		self.tabWidget.addTab(self.tab3, "Material Settings")
		self.tab4 = QtGui.QWidget()
		self.tabWidget.addTab(self.tab4, "Excitation Settings")

		#setting layout for each tab
		self.tab1.setLayout(QtGui.QHBoxLayout())
		self.tab2.setLayout(QtGui.QHBoxLayout())
		self.tab3.setLayout(QtGui.QHBoxLayout())
		self.tab4.setLayout(QtGui.QHBoxLayout())

		#######################################################################################
		#  OBJECT ASSIGNMENTS TAB
		#######################################################################################

		#
		#  LuboJ Tree Widget
		#
		self.treeWidget = QtGui.QTreeWidget(self)
		self.treeWidget.setColumnCount(1)
		self.treeWidget.setHeaderLabels(["Available objects"])
		self.treeWidget.setGeometry(30,50,400,500)
		self.treeWidget.setParent(self.tab1)

		items = OpenEMS.getAllObjects()
		#items = OpenEMS.getOpenEMSObjects()
		self.treeWidget.insertTopLevelItems(0, items)

		#
		#  LuboJ textInput Widget
		#
		self.textInput2 = QtGui.QLineEdit(self)
		self.textInput2.setText("-----------")
		self.textInput2.setFixedWidth(190)
		self.textInput2.move(30, 570)
		self.textInput2.setParent(self.tab1)

		#
		#  LuboJ Tree Widget 2
		#
		self.treeWidget2 = QtGui.QTreeWidget(self)
		self.treeWidget2.setColumnCount(1)
		self.treeWidget2.setGeometry(530,50,400,500)
		self.treeWidget2.setHeaderLabels(["Simulation parameters"])
		self.treeWidget2.setParent(self.tab1)

		#
		# TOP LEVEL ITEMS (excitation, grid, materials, ...)
		#

		# MATERIALS
		topItem = QtGui.QTreeWidgetItem(["Materials"])
		topItem.setIcon(0, QtGui.QIcon(".\\img\\material.png"))
		self.treeWidget2.insertTopLevelItem(0, topItem)

		# EXCITATION
		topItem = QtGui.QTreeWidgetItem(["Excitation"])
		topItem.setIcon(0, QtGui.QIcon(".\\img\\bulb.png"))
		self.treeWidget2.insertTopLevelItem(0, topItem)

		# GRID
		topItem = QtGui.QTreeWidgetItem(["Grid"])
		topItem.setIcon(0, QtGui.QIcon(".\\img\\grid.png"))
		self.treeWidget2.insertTopLevelItem(0, topItem)

		#
		# Default items for each section
		#
		topItem = self.treeWidget2.itemAt(0,0)
		defaultMaterialItem = QtGui.QTreeWidgetItem(["Default"])
		defaultExcitationItem = QtGui.QTreeWidgetItem(["Default"])
		defaultGridItem = QtGui.QTreeWidgetItem(["Default"])

		self.treeWidget2.topLevelItem(0).addChildren([defaultMaterialItem])
		self.treeWidget2.topLevelItem(1).addChildren([defaultExcitationItem])
		self.treeWidget2.topLevelItem(2).addChildren([defaultGridItem])

		# << button
		moveLeftButton = QtGui.QPushButton('<<', self)
		moveLeftButton.clicked.connect(self.onMoveLeft)
		moveLeftButton.setAutoDefault(True)
		moveLeftButton.setGeometry(460,390,40,30)
		moveLeftButton.setParent(self.tab1)

		# >> button
		moveRightButton = QtGui.QPushButton('>>', self)
		moveRightButton.clicked.connect(self.onMoveRight)
		moveRightButton.setAutoDefault(True)
		moveRightButton.setGeometry(460,330,40,30)
		moveRightButton.setParent(self.tab1)

		#######################################################################################
		#  GRID SETTINGS TAB
		#######################################################################################

		self.gridObjectsTreeWidget = QtGui.QTreeWidget(self)
		self.gridObjectsTreeWidget.setMinimumWidth(400)
		self.gridObjectsTreeWidget.setMinimumHeight(500)
		self.gridObjectsTreeWidget.setHeaderLabels(["Grid settings"])
		self.tab2.layout().addWidget(self.gridObjectsTreeWidget)

		self.gridObjectSettingsWidget = QtGui.QWidget(self)
		self.gridObjectSettingsWidget.setMinimumWidth(400)
		self.gridObjectSettingsWidget.setMinimumHeight(500)
		self.gridObjectSettingsWidget.setLayout(QtGui.QVBoxLayout())

		self.tab2.layout().addWidget(self.gridObjectSettingsWidget)

		#these here are just test layout
		button1 = QtGui.QPushButton("One")
		button2 = QtGui.QPushButton("Two")
		button3 = QtGui.QPushButton("Three")
		button4 = QtGui.QPushButton("Four")
		button5 = QtGui.QPushButton("Five")
		self.gridObjectSettingsWidget.layout().addWidget(button1)
		self.gridObjectSettingsWidget.layout().addWidget(button2)
		self.gridObjectSettingsWidget.layout().addWidget(button3)
		self.gridObjectSettingsWidget.layout().addWidget(button4)
		self.gridObjectSettingsWidget.layout().addWidget(button5)
		

		# now make the window visible
		self.show()
		#

	def onMoveLeft(self):
		print("Button << clicked.")

	def onMoveRight(self):
		print("Button >> clicked.")
		leftItem = self.treeWidget.selectedItems()[0].clone()
		rightItem = self.treeWidget2.selectedItems()[0]
		print(leftItem.text(0))
		print(rightItem.text(0))

		rightItem.addChild(leftItem)

	def treeWidgetItemChangedHandler(self, item, column):
		self.textInput2.setText(item.data(0,QtCore.Qt.UserRole))

# Class definitions

# Function definitions

# Constant definitions
userCancelled		= "Cancelled"
userOK			= "OK"

# code ***********************************************************************************

form = ExampleModalGuiClass()
form.exec_()

if form.result==userCancelled:
	pass # steps to handle user clicking Cancel
if form.result==userOK:
	# steps to handle user clicking OK
	localVariable1 = form.label1.text()
	localVariable2 = form.label2.text()
	localVariable3 = form.label3.text()
	localVariable4 = form.label4.text()
	print(localVariable1)
	print(localVariable2)
	print(localVariable3)
	print(localVariable4)
#
#OS: Mac OS X
#Word size: 64-bit
#Version: 0.14.3703 (Git)
#Branch: releases/FreeCAD-0-14
#Hash: c6edd47334a3e6f209e493773093db2b9b4f0e40
#Python version: 2.7.5
#Qt version: 4.8.6
#Coin version: 3.1.3
#SoQt version: 1.5.0
#OCC version: 6.7.0
#
